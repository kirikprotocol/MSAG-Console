-- Copyright 2008 Sibinco. All Rights Reserved
-- HISTORY
-- 2008-12-09  Dmitry Bukin     created

    SIBINCO-MSAG-MIB DEFINITIONS ::= BEGIN
    IMPORTS
        sibinco 
    FROM SIBINCO-SMSC-MIB;

    -- sibinco is 1.3.6.1.4.1.26757

    -- 1.3.6.1.4.1.26757.2
    msag OBJECT IDENTIFIER ::= { sibinco 2 }

    -- 1.3.6.1.4.1.26757.2.0
    msagnotifications OBJECT IDENTIFIER ::= { msag 0 }

-- trap section

    -- 1.3.6.1.4.1.26757.2.5
    alertMessage OBJECT-TYPE
    SYNTAX DisplayString
    MAX-ACCESS accessible-for-notify
    STATUS current
    DESCRIPTION
    "The string object containing textual description of alert."
    ::= { msag 5 }

    -- 1.3.6.1.4.1.26757.2.7
    alertSeverity OBJECT-TYPE
    SYNTAX  INTEGER {
    normal(1),
    warning(2),
    minor(3),
    major(4),
    critical(5)
    }
    MAX-ACCESS  read-write
    STATUS      current
    DESCRIPTION "Severity of alert"
    ::= { msag 7 }

    -- 1.3.6.1.4.1.26757.2.8
    alertId OBJECT-TYPE
    SYNTAX  DisplayString
    MAX-ACCESS  read-write
    STATUS      current
    DESCRIPTION "Identifier of alert (e.g. object id)"
    ::= { msag 8 }

    -- 1.3.6.1.4.1.26757.2.9
    alertObjCategory OBJECT-TYPE
    SYNTAX  DisplayString
    MAX-ACCESS  read-write
    STATUS      current
    DESCRIPTION "Object category."
    ::= { msag 9 }

    msagNewAlertFFMR NOTIFICATION-TYPE
    OBJECTS { alertMessage, alertSeverity, alertObjCategory, alertId }
    STATUS current
    DESCRIPTION
    "Notify about msag events"
    ::= { msagnotifications 4 }

    msagClearAlertFFMR NOTIFICATION-TYPE
    OBJECTS { alertMessage, alertSeverity, alertObjCategory, alertId }
    STATUS current
    DESCRIPTION
    "Notify about msag events"
    ::= { msagnotifications 5 }

    END
