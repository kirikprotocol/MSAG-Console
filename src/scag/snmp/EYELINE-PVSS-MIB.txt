-- Copyright 2008 Sibinco. All Rights Reserved
-- HISTORY
-- 2008-12-09  Dmitry Bukin     created
-- 2010-01-26  Dmitry Bukin     renamed to EYELINE prefix, more traps added

    EYELINE-PVSS-MIB DEFINITIONS ::= BEGIN
    IMPORTS
        sibinco 
    FROM SIBINCO-SMSC-MIB
        DisplayString
    FROM SNMPv2-TC;

    -- sibinco is 1.3.6.1.4.1.26757
    -- sibinco is iso.org.dod.internet.private.enterprises.sibinco

    -- 1.3.6.1.4.1.26757.3
    pvss OBJECT IDENTIFIER ::= { sibinco 3 }

    -- 1.3.6.1.4.1.26757.3.1
    pvssDescr OBJECT-TYPE
    SYNTAX  DisplayString
    MAX-ACCESS  read-only
    STATUS  current
    DESCRIPTION
    "Version string"
    ::= { pvss 1 }

    -- 1.3.6.1.4.1.26757.3.4
    pvssCounterTable OBJECT-TYPE
    SYNTAX  SEQUENCE OF PvssCounterEntry
    MAX-ACCESS  not-accessible
    STATUS  current
    DESCRIPTION
    "PVSS Counter table."
    ::= { pvss 4 }

    -- 1.3.6.1.4.1.26757.3.4.1
    pvssCounterEntry OBJECT-TYPE
    SYNTAX  PvssCounterEntry
    MAX-ACCESS  not-accessible
    STATUS  current
    DESCRIPTION
    "PVSS Counter entry."
    INDEX { pvssCounterIndex }
    ::= { pvssCounterTable 1 }

    PvssCounterEntry ::=
    SEQUENCE {
    pvssCounterIndex INTEGER,
    pvssCounterName  DisplayString,
    pvssCounterValue Counter64
    }

    -- 1.3.6.1.4.1.26757.3.4.1.1
    pvssCounterIndex OBJECT-TYPE
    SYNTAX INTEGER(0..32768)
    MAX-ACCESS read-only
    STATUS current
    DESCRIPTION
    "PVSS Counter Index"
    ::= { pvssCounterEntry 1 }

    -- 1.3.6.1.4.1.26757.3.4.1.2
    pvssCounterName OBJECT-TYPE
    SYNTAX DisplayString (SIZE (0..48))
    MAX-ACCESS  read-only
    STATUS  current
    DESCRIPTION
    "PVSS Counter Name."
    ::= { pvssCounterEntry 2 }

    -- 1.3.6.1.4.1.26757.3.4.1.3
    pvssCounterValue OBJECT-TYPE
    SYNTAX Counter64
    MAX-ACCESS read-only
    STATUS  current
    DESCRIPTION
    "PVSS Counter Value."
    ::= { pvssCounterEntry 3 }

    END
