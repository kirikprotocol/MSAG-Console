-- Copyright 2008 Sibinco. All Rights Reserved
-- HISTORY
-- 2008-12-09  Dmitry Bukin     created
-- 2010-01-26  Dmitry Bukin     renamed to EYELINE prefix, more traps added
-- 2014-09-01  Sergey Khomutinnikov ksv@eyeline.mobi	add smeStatTable, smeErrTable, routeStatTable, routeErrTable

    EYELINE-MSAG-MIB DEFINITIONS ::= BEGIN
    IMPORTS
        sibinco 
    FROM SIBINCO-SMSC-MIB
        DisplayString
    FROM SNMPv2-TC;

    -- sibinco is 1.3.6.1.4.1.26757
    -- sibinco is iso.org.dod.internet.private.enterprises.sibinco

    -- 1.3.6.1.4.1.26757.2
    msag OBJECT IDENTIFIER ::= { sibinco 2 }

    -- 1.3.6.1.4.1.26757.2.0
    msagnotifications OBJECT IDENTIFIER ::= { msag 0 }

    -- 1.3.6.1.4.1.26757.2.1
    msagDescr OBJECT-TYPE
    SYNTAX  DisplayString
    MAX-ACCESS  read-only
    STATUS  current
    DESCRIPTION
    "Version string"
    ::= { msag 1 }

    -- 1.3.6.1.4.1.26757.2.2
    msagStatus OBJECT-TYPE
    SYNTAX  DisplayString
    MAX-ACCESS  read-only
    STATUS  current
    DESCRIPTION
    "MSAG status"
    ::= { msag 2 }

    -- 1.3.6.1.4.1.26757.2.3
    msagUptime OBJECT-TYPE
    SYNTAX  DisplayString
    MAX-ACCESS  read-only
    STATUS  current
    DESCRIPTION
    "MSAG uptime"
    ::= { msag 3 }

    -- 1.3.6.1.4.1.26757.2.3.0
    msagUptimeFormatted OBJECT-TYPE
    SYNTAX  DisplayString
    MAX-ACCESS  read-only
    STATUS  current
    DESCRIPTION
    "MSAG uptime formatted"
    ::= { msagUptime 0 }


    -- 1.3.6.1.4.1.26757.2.4
    msagCounterTable OBJECT-TYPE
    SYNTAX  SEQUENCE OF MsagCounterEntry
    MAX-ACCESS  not-accessible
    STATUS  current
    DESCRIPTION
    "MSAG Counter table."
    ::= { msag 4 }

    -- 1.3.6.1.4.1.26757.2.4.1
    msagCounterEntry OBJECT-TYPE
    SYNTAX  MsagCounterEntry
    MAX-ACCESS  not-accessible
    STATUS  current
    DESCRIPTION
    "MSAG Counter entry."
    INDEX { msagCounterIndex }
    ::= { msagCounterTable 1 }

    MsagCounterEntry ::=
    SEQUENCE {
    msagCounterIndex INTEGER,
    msagCounterName  DisplayString,
    msagCounterValue Counter64
    }

    -- 1.3.6.1.4.1.26757.2.4.1.1
    msagCounterIndex OBJECT-TYPE
    SYNTAX INTEGER(0..32768)
    MAX-ACCESS read-only
    STATUS current
    DESCRIPTION
    "MSAG Counter Index"
    ::= { msagCounterEntry 1 }

    -- 1.3.6.1.4.1.26757.2.4.1.2
    msagCounterName OBJECT-TYPE
    SYNTAX DisplayString (SIZE (0..48))
    MAX-ACCESS  read-only
    STATUS  current
    DESCRIPTION
    "MSAG Counter Name."
    ::= { msagCounterEntry 2 }

    -- 1.3.6.1.4.1.26757.2.4.1.3
    msagCounterValue OBJECT-TYPE
    SYNTAX Counter64
    MAX-ACCESS read-only
    STATUS  current
    DESCRIPTION
    "MSAG Counter Value."
    ::= { msagCounterEntry 3 }


-- trap section

    -- 1.3.6.1.4.1.26757.2.5
    alertMessage OBJECT-TYPE
    SYNTAX DisplayString
    MAX-ACCESS accessible-for-notify
    STATUS current
    DESCRIPTION
    "The string object containing textual description of alert."
    ::= { msag 5 }

    -- 1.3.6.1.4.1.26757.2.7
    alertSeverity OBJECT-TYPE
    SYNTAX  INTEGER {
    normal(1),
    warning(2),
    minor(3),
    major(4),
    critical(5)
    }
    -- MAX-ACCESS  read-write
    MAX-ACCESS not-accessible
    STATUS      current
    DESCRIPTION "Severity of alert"
    ::= { msag 7 }

    -- 1.3.6.1.4.1.26757.2.8
    alertId OBJECT-TYPE
    SYNTAX  DisplayString
    -- MAX-ACCESS  read-write
    MAX-ACCESS  not-accessible
    STATUS      current
    DESCRIPTION "Identifier of alert (e.g. object id)"
    ::= { msag 8 }

    -- 1.3.6.1.4.1.26757.2.9
    alertObjCategory OBJECT-TYPE
    SYNTAX  DisplayString
    -- MAX-ACCESS  read-write
    MAX-ACCESS  not-accessible
    STATUS      current
    DESCRIPTION "Object category."
    ::= { msag 9 }

-- Compound trap objects

    -- 1.3.6.1.4.1.26757.2.0.4
    -- trap is sent when an ESME has problems with connection
    msagNewAlertFFMR NOTIFICATION-TYPE
    OBJECTS { alertMessage, alertSeverity, alertObjCategory, alertId }
    STATUS current
    DESCRIPTION
    "Notify about msag events"
    ::= { msagnotifications 4 }

    -- 1.3.6.1.4.1.26757.2.0.5
    -- trap is sent when an ESME fixed problems with connection
    msagClearAlertFFMR NOTIFICATION-TYPE
    OBJECTS { alertMessage, alertSeverity, alertObjCategory, alertId }
    STATUS current
    DESCRIPTION
    "Notify about msag events"
    ::= { msagnotifications 5 }

    -- 1.3.6.1.4.1.26757.2.0.6
    -- trap is sent to report about config loading
    msagLoadConfig NOTIFICATION-TYPE
    OBJECTS { alertMessage, alertSeverity, alertObjCategory, alertId }
    STATUS current
    DESCRIPTION
    "Notify about msag config loading events"
    ::= { msagnotifications 6 }
    
    -- 1.3.6.1.4.1.26757.2.0.7
    -- trap is sent to report the total msag traffic events
    msagTraffic NOTIFICATION-TYPE
    OBJECTS { alertMessage, alertSeverity, alertObjCategory, alertId }
    STATUS current
    DESCRIPTION
    "Notify about msag total traffic events"
    ::= { msagnotifications 7 }
    
    -- 1.3.6.1.4.1.26757.2.0.8
    -- trap is sent to report the total msag traffic events
    msagSMPPEndPointTraffic NOTIFICATION-TYPE
    OBJECTS { alertMessage, alertSeverity, alertObjCategory, alertId }
    STATUS current
    DESCRIPTION
    "Notify about particular ESME msag traffic events"
    ::= { msagnotifications 8 }
    
    -- 1.3.6.1.4.1.26757.2.0.9
    msagSMPPQueueLimit NOTIFICATION-TYPE
    OBJECTS { alertMessage, alertSeverity, alertObjCategory, alertId }
    STATUS current
    DESCRIPTION
    "Notify about SMPP queue events"
    ::= { msagnotifications 9 }

    -- 1.3.6.1.4.1.26757.2.0.10
    msagSessionLimit NOTIFICATION-TYPE
    OBJECTS { alertMessage, alertSeverity, alertObjCategory, alertId }
    STATUS current
    DESCRIPTION
    "Notify about session events"
    ::= { msagnotifications 10 }

    -- 1.3.6.1.4.1.26757.2.0.11
    msagSMPPConnect NOTIFICATION-TYPE
    OBJECTS { alertMessage, alertSeverity, alertObjCategory, alertId }
    STATUS current
    DESCRIPTION
    "Notify about connection blocking"
    ::= { msagnotifications 11 }
    
    -- 1.3.6.1.4.1.26757.2.0.12
    msagAlive NOTIFICATION-TYPE
    OBJECTS { alertMessage, alertSeverity, alertObjCategory, alertId }
    STATUS current
    DESCRIPTION
    "Notify periodically about msag being alive"
    ::= { msagnotifications 12 }

-- sme stat table

    -- 1.3.6.1.4.1.26757.2.10
    -- smeStatTable is sent on request as SME counters stats (like in smsc)
  smeStatTable OBJECT-TYPE
      SYNTAX  SEQUENCE OF SmeStatEntry
      MAX-ACCESS  not-accessible
      STATUS  current
      DESCRIPTION
    "SME Stats table."
      ::= { msag 10 }


    -- 1.3.6.1.4.1.26757.2.10.1
    -- smeStatEntry is a smeStatTable row
  smeStatEntry OBJECT-TYPE
      SYNTAX  SmeStatEntry
      MAX-ACCESS  not-accessible
      STATUS  current
      DESCRIPTION
    "A route to a particular destination."
      INDEX   { smeStatIndex }
      ::= { smeStatTable 1 }

  SmeStatEntry ::=
      SEQUENCE {
    smeStatIndex INTEGER,
    smeStatSystemId DisplayString,
    smeStatAccepted  Counter64,
    smeStatRejected  Counter64,
    smeStatDelivered Counter64,
    smeStatGwRejected  Counter64,
    smeStatFailed    Counter64,
    smeStatReceiptOk  Counter64,
    smeStatReceiptFailed Counter64
      }

    -- 1.3.6.1.4.1.26757.2.10.1.1
  smeStatIndex OBJECT-TYPE
      SYNTAX  INTEGER(0..2000)
      MAX-ACCESS  read-only
      STATUS  current
      DESCRIPTION
    "SME Index."
      ::= { smeStatEntry 1 }

    -- 1.3.6.1.4.1.26757.2.10.1.2
  smeStatSystemId OBJECT-TYPE
      SYNTAX  DisplayString (SIZE (0..32))
      MAX-ACCESS  read-only
      STATUS  current
      DESCRIPTION
    "SME system Id."
      ::= { smeStatEntry 2 }

    -- 1.3.6.1.4.1.26757.2.10.1.3
  smeStatAccepted OBJECT-TYPE
      SYNTAX  Counter64
      MAX-ACCESS  read-only
      STATUS  current
      DESCRIPTION
    "SME Counter Accepted"
      ::= { smeStatEntry 3 }

    -- 1.3.6.1.4.1.26757.2.10.1.4
  smeStatRejected OBJECT-TYPE
      SYNTAX  Counter64
      MAX-ACCESS  read-only
      STATUS  current
      DESCRIPTION
    "SME Counter Rejected"
      ::= { smeStatEntry 4 }

    -- 1.3.6.1.4.1.26757.2.10.1.5
  smeStatDelivered OBJECT-TYPE
      SYNTAX  Counter64
      MAX-ACCESS  read-only
      STATUS  current
      DESCRIPTION
    "SME Counter Delivered"
      ::= { smeStatEntry 5 }

    -- 1.3.6.1.4.1.26757.2.10.1.6
  smeStatRejected OBJECT-TYPE
      SYNTAX  Counter64
      MAX-ACCESS  read-only
      STATUS  current
      DESCRIPTION
    "SME Counter Rejected"
      ::= { smeStatEntry 6 }

    -- 1.3.6.1.4.1.26757.2.10.1.7
  smeStatFailed OBJECT-TYPE
      SYNTAX  Counter64
      MAX-ACCESS  read-only
      STATUS  current
      DESCRIPTION
    "SME Counter Failed"
      ::= { smeStatEntry 7 }

    -- 1.3.6.1.4.1.26757.2.10.1.8
  smeStatReceiptOk OBJECT-TYPE
      SYNTAX  Counter64
      MAX-ACCESS  read-only
      STATUS  current
      DESCRIPTION
    "SME Counter Receipt Ok"
      ::= { smeStatEntry 8 }

    -- 1.3.6.1.4.1.26757.2.10.1.9
  smeStatReceiptFailed OBJECT-TYPE
      SYNTAX  Counter64
      MAX-ACCESS  read-only
      STATUS  current
      DESCRIPTION
    "SME Counter Receipt Failed"
      ::= { smeStatEntry 9 }


  -- 1.3.6.1.4.1.26757.2.11
  smeErrTable OBJECT-TYPE
      SYNTAX  SEQUENCE OF SmeErrEntry
      MAX-ACCESS  not-accessible
      STATUS  current
      DESCRIPTION
    "SME Errors table."
      ::= { msag 11 }

  smeErrEntry OBJECT-TYPE
      SYNTAX  SmeErrEntry
      MAX-ACCESS  not-accessible
      STATUS  current
      DESCRIPTION
    "A route to a particular destination."
      INDEX   { smeErrIndex,smeErrCode }
      ::= { smeErrTable 1 }

  SmeErrEntry ::=
      SEQUENCE {
    smeErrIndex INTEGER,
    smeErrCode INTEGER,
    smeErrSystemId DisplayString,
    smeErrCount  Counter64
      }

  smeErrIndex OBJECT-TYPE
      SYNTAX  INTEGER(0..2000)
      MAX-ACCESS  read-only
      STATUS  current
      DESCRIPTION
    "SME Index."
      ::= { smeErrEntry 1 }

  smeErrCode OBJECT-TYPE
      SYNTAX  INTEGER(0..2000)
      MAX-ACCESS  read-only
      STATUS  current
      DESCRIPTION
    "SME Err Code."
      ::= { smeErrEntry 2 }

  smeErrSystemId OBJECT-TYPE
      SYNTAX  DisplayString (SIZE (0..32))
      MAX-ACCESS  read-only
      STATUS  current
      DESCRIPTION
    "SME system Id."
      ::= { smeErrEntry 3 }

  smeErrCount OBJECT-TYPE
      SYNTAX  Counter64
      MAX-ACCESS  read-only
      STATUS  current
      DESCRIPTION
    "SME Counter Accepted"
      ::= { smeErrEntry 4 }


-- route stat table

    -- 1.3.6.1.4.1.26757.2.12
    -- routeStatTable is sent on request as Route counters stats
  routeStatTable OBJECT-TYPE
      SYNTAX  SEQUENCE OF RouteStatEntry
      MAX-ACCESS  not-accessible
      STATUS  current
      DESCRIPTION
    "Route Stats table."
      ::= { msag 12 }

    -- 1.3.6.1.4.1.26757.2.12.1
    -- routeStatEntry is a routeStatTable row
  routeStatEntry OBJECT-TYPE
      SYNTAX  RouteStatEntry
      MAX-ACCESS  not-accessible
      STATUS  current
      DESCRIPTION
    "A route to a particular destination."
      INDEX   { routeStatIndex }
      ::= { routeStatTable 1 }

  RouteStatEntry ::=
      SEQUENCE {
    routeStatIndex INTEGER,
    routeStatRouteId DisplayString,
    routeStatAccepted  Counter64,
    routeStatRejected  Counter64,
    routeStatDelivered Counter64,
    routeStatGwRejected  Counter64,
    routeStatFailed    Counter64,
    routeStatReceiptOk  Counter64,
    routeStatReceiptFailed Counter64
      }

    -- 1.3.6.1.4.1.26757.2.12.1.1
  routeStatIndex OBJECT-TYPE
      SYNTAX  INTEGER(0..2000)
      MAX-ACCESS  read-only
      STATUS  current
      DESCRIPTION
    "Route Index."
      ::= { routeStatEntry 1 }

    -- 1.3.6.1.4.1.26757.2.12.1.2
  routeStatRouteId OBJECT-TYPE
      SYNTAX  DisplayString (SIZE (0..32))
      MAX-ACCESS  read-only
      STATUS  current
      DESCRIPTION
    "Route system Id."
      ::= { routeStatEntry 2 }

    -- 1.3.6.1.4.1.26757.2.12.1.3
  routeStatAccepted OBJECT-TYPE
      SYNTAX  Counter64
      MAX-ACCESS  read-only
      STATUS  current
      DESCRIPTION
    "Route Counter Accepted"
      ::= { routeStatEntry 3 }

    -- 1.3.6.1.4.1.26757.2.12.1.4
  routeStatRejected OBJECT-TYPE
      SYNTAX  Counter64
      MAX-ACCESS  read-only
      STATUS  current
      DESCRIPTION
    "Route Counter Rejected"
      ::= { routeStatEntry 4 }

    -- 1.3.6.1.4.1.26757.2.12.1.5
  routeStatDelivered OBJECT-TYPE
      SYNTAX  Counter64
      MAX-ACCESS  read-only
      STATUS  current
      DESCRIPTION
    "Route Counter Delivered"
      ::= { routeStatEntry 5 }

    -- 1.3.6.1.4.1.26757.2.12.1.6
  routeStatRejected OBJECT-TYPE
      SYNTAX  Counter64
      MAX-ACCESS  read-only
      STATUS  current
      DESCRIPTION
    "Route Counter Rejected"
      ::= { routeStatEntry 6 }

    -- 1.3.6.1.4.1.26757.2.12.1.7
  routeStatFailed OBJECT-TYPE
      SYNTAX  Counter64
      MAX-ACCESS  read-only
      STATUS  current
      DESCRIPTION
    "Route Counter Failed"
      ::= { routeStatEntry 7 }

    -- 1.3.6.1.4.1.26757.2.12.1.8
  routeStatReceiptOk OBJECT-TYPE
      SYNTAX  Counter64
      MAX-ACCESS  read-only
      STATUS  current
      DESCRIPTION
    "Route Counter Receipt Ok"
      ::= { routeStatEntry 8 }

    -- 1.3.6.1.4.1.26757.2.12.1.9
  routeStatReceiptFailed OBJECT-TYPE
      SYNTAX  Counter64
      MAX-ACCESS  read-only
      STATUS  current
      DESCRIPTION
    "Route Counter Receipt Failed"
      ::= { routeStatEntry 9 }


  -- 1.3.6.1.4.1.26757.2.13
  routeErrTable OBJECT-TYPE
      SYNTAX  SEQUENCE OF RouteErrEntry
      MAX-ACCESS  not-accessible
      STATUS  current
      DESCRIPTION
    "Route Errors table."
      ::= { msag 13 }

  routeErrEntry OBJECT-TYPE
      SYNTAX  RouteErrEntry
      MAX-ACCESS  not-accessible
      STATUS  current
      DESCRIPTION
    "A route to a particular destination."
      INDEX   { routeErrIndex,routeErrCode }
      ::= { routeErrTable 1 }

  RouteErrEntry ::=
      SEQUENCE {
    routeErrIndex INTEGER,
    routeErrCode INTEGER,
    routeErrId DisplayString,
    routeErrCount  Counter64
      }

  routeErrIndex OBJECT-TYPE
      SYNTAX  INTEGER(0..2000)
      MAX-ACCESS  read-only
      STATUS  current
      DESCRIPTION
    "Route Index."
      ::= { routeErrEntry 1 }

  routeErrCode OBJECT-TYPE
      SYNTAX  INTEGER(0..2000)
      MAX-ACCESS  read-only
      STATUS  current
      DESCRIPTION
    "Route Err Code."
      ::= { routeErrEntry 2 }

  routeErrId OBJECT-TYPE
      SYNTAX  DisplayString (SIZE (0..32))
      MAX-ACCESS  read-only
      STATUS  current
      DESCRIPTION
    "Route Id."
      ::= { routeErrEntry 3 }

  routeErrCount OBJECT-TYPE
      SYNTAX  Counter64
      MAX-ACCESS  read-only
      STATUS  current
      DESCRIPTION
    "Route Error Counter."
      ::= { routeErrEntry 4 }

    END
