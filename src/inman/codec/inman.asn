/* $Id$ */
/* ************************************************************************** *
 * This file contains ASN.1 definitions for PDUs (components from cap4SMS     *
 * CONTRACT) utilized by IN-Manager					      *
 * ************************************************************************** *
 * Author: R.V. Gerasimov						      *
 * ************************************************************************** */
IN-Maneger-OIDs
-- OIDs of modules used by IN-Manager
DEFINITIONS ::=
-- GVRoman's NOTE: This module is for informative purposes only. 
-- SourceForge's asn1c unable to parse ASN.1 module references by named OID.
-- So, actually, these OIDs are never used in below notations.
BEGIN

ros-InformationObjects OBJECT IDENTIFIER ::=
    { joint-iso-itu-t remote-operations(4) informationObjects(5) version1(0) }

-- MAP-MS-DataTypes
map-MS-DataTypes OBJECT IDENTIFIER ::=
    { itu-t identified-organization(4) etsi(0) mobileDomain(0)
      gsm-Network(1) modules(3) map-MS-DataTypes(11) version8(8) }

-- MAP-CH-DataTypes
map-CH-DataTypes OBJECT IDENTIFIER ::=
    { itu-t identified-organization(4) etsi(0) mobileDomain(0)
      gsm-Network(1) modules(3) map-CH-DataTypes(13) version8(8) }

-- MAP-CommonDataTypes
map-CommonDataTypes OBJECT IDENTIFIER ::=
    { itu-t(0) identified-organization(4) etsi(0) mobileDomain(0) gsm-Network(1)
      modules(3) map-CommonDataTypes(18) version8(8) }
      
-- MAP-ExtensionDataTypes
map-Ext-DataTypes OBJECT IDENTIFIER ::=
    { itu-t identified-organization(4) etsi(0) mobileDomain(0) gsm-Network(1)
      modules(3) map-ExtensionDataTypes(21) version8(8) }

-- CS1-DataTypes
cs1-DataTypes OBJECT IDENTIFIER ::= 
    { itu-t(0) identified-organization(4) etsi(0) inDomain(1)
      in-network(1) modules(0) cs1-datatypes(2) version1(0) }

-- CS2-datatypes
in-CS2-datatypes OBJECT IDENTIFIER ::= 
    { itu-t(0) identified-organization(4) etsi(0) inDomain(1)
      in-network(1) cs2(20) modules(0) in-cs2-datatypes(0) version1(0) }

-- CAP-datatypes 
cap-datatypes OBJECT IDENTIFIER ::=
    { itu-t(0) identified-organization(4) etsi(0) mobileDomain(0)
      umts-network(1) modules(3) cap-datatypes(52) version4(3) } 

cap-errorcodes OBJECT IDENTIFIER ::=
    { itu-t(0) identified-organization(4) etsi(0) mobileDomain(0) umts-network(1)
      modules(3) cap-errorcodes(57) version4(3) }

cap-errortypes OBJECT IDENTIFIER ::=
    { itu-t(0) identified-organization(4) etsi(0) mobileDomain(0) umts-network(1)
      modules(3) cap-errortypes(51) version4(3) }

-- CAP-classes
cap-classes OBJECT IDENTIFIER ::=
    { itu-t(0) identified-organization(4) etsi(0) mobileDomain(0)
      umts-network(1) modules(3) cap-classes(54) version4(3) }

cap-smsSSF-gsmSCF-Protocol OBJECT IDENTIFIER ::=
    { itu-t(0) identified-organization(4) etsi(0) mobileDomain(0) umts-network(1)
      modules(3) cap-smsSSF-gsmSCF-pkgs-contracts-acs(106) version4(3) }

END -- IN-Maneger-OIDs

-- ******************************************************************* --
-- ROS modules follow
-- ******************************************************************* --

-- Module Remote-Operations-Information-Objects (X.880:07/1994)
Remote-Operations-Information-Objects {joint-iso-itu-t remote-operations(4)
  informationObjects(5) version1(0)}
DEFINITIONS ::=
-- GVRoman's NOTE: 
-- this is reduced version of original module containing only types required for IN-Manager
BEGIN

OPERATION ::= CLASS {
  &ArgumentType          OPTIONAL,
  &argumentTypeOptional  BOOLEAN OPTIONAL,
  &returnResult          BOOLEAN DEFAULT TRUE,
  &ResultType            OPTIONAL,
  &resultTypeOptional    BOOLEAN OPTIONAL,
  &Errors                ERROR OPTIONAL,
  &Linked                OPERATION OPTIONAL,
  &synchronous           BOOLEAN DEFAULT FALSE,
  &alwaysReturns         BOOLEAN DEFAULT TRUE,
  &InvokePriority        Priority OPTIONAL,
  &ResultPriority        Priority OPTIONAL,
  &operationCode         Code UNIQUE OPTIONAL
}
WITH SYNTAX {
  [ARGUMENT &ArgumentType
   [OPTIONAL &argumentTypeOptional]]
  [RESULT &ResultType
   [OPTIONAL &resultTypeOptional]]
  [RETURN RESULT &returnResult]
  [ERRORS &Errors]
  [LINKED &Linked]
  [SYNCHRONOUS &synchronous]
  [ALWAYS RESPONDS &alwaysReturns]
  [INVOKE PRIORITY &InvokePriority]
  [RESULT-PRIORITY &ResultPriority]
  [CODE &operationCode]
}

ERROR ::= CLASS {
  &ParameterType          OPTIONAL,
  &parameterTypeOptional  BOOLEAN OPTIONAL,
  &ErrorPriority          Priority OPTIONAL,
  &errorCode              Code UNIQUE OPTIONAL
}
WITH SYNTAX {
  [PARAMETER &ParameterType
   [OPTIONAL &parameterTypeOptional]]
  [PRIORITY &ErrorPriority]
  [CODE &errorCode]
}

Code ::= CHOICE {local   INTEGER,
                 global  OBJECT IDENTIFIER
}

Priority ::= INTEGER(0..MAX)

END -- end of Information Object specifications


-- ******************************************************************* --
-- INAP modules follow
-- ******************************************************************* --

CS1-DataTypes {itu-t(0) identified-organization(4) etsi(0) inDomain(1)
  in-network(1) modules(0) cs1-datatypes(2) version1(0)}
-- This module contains the type definitions for the IN CS1 data types.
DEFINITIONS IMPLICIT TAGS ::=
-- GVRoman's NOTE: 
-- this is reduced version of original module containing only types required for IN-Manager
BEGIN

-- Information that allows the SCF to choose the appropriate service logic.
ServiceKey ::= Integer4

Integer4 ::= INTEGER(0..2147483647)

END -- CS1-DataTypes


IN-CS2-datatypes {itu-t(0) identified-organization(4) etsi(0) inDomain(1)
in-network(1) cs2(20) modules(0) in-cs2-datatypes (0) version1(0)}
DEFINITIONS IMPLICIT TAGS ::=
-- GVRoman's NOTE: 
-- this is reduced version of original module containing only types required for IN-Manager
BEGIN

CriticalityType	::= ENUMERATED { ignore (0), abort (1) } 

MiscCallInfo	::= SEQUENCE {
    messageType	[0]	ENUMERATED { request (0), notification (1), ... }
}

END -- IN-CS2-datatypes

-- ******************************************************************* --
-- MAP modules follow
-- ******************************************************************* --

-- 17.7.1	Mobile Service data types
MAP-MS-DataTypes {itu-t identified-organization(4) etsi(0) mobileDomain(0)
  gsm-Network(1) modules(3) map-MS-DataTypes(11) version8(8)}
DEFINITIONS IMPLICIT TAGS ::=
-- GVRoman's NOTE: 
-- this is reduced version of original module containing only types required for IN-Manager
BEGIN

IMPORTS
  AddressString, ISDN-AddressString, CellGlobalIdOrServiceAreaIdOrLAI,
  AgeOfLocationInformation
    FROM MAP-CommonDataTypes {itu-t(0) identified-organization(4) etsi(0)
      mobileDomain(0) gsm-Network(1) modules(3) map-CommonDataTypes(18)
      version8(8)}
  ExtensionContainer
    FROM MAP-ExtensionDataTypes {itu-t(0) identified-organization(4) etsi(0)
      mobileDomain(0) gsm-Network(1) modules(3) map-ExtensionDataTypes(21)
      version8(8)}
    ;

LocationInformation ::= SEQUENCE {
  ageOfLocationInformation          AgeOfLocationInformation OPTIONAL,
  geographicalInformation           [0]  GeographicalInformation OPTIONAL,
  vlr-number                        [1]  ISDN-AddressString OPTIONAL,
  locationNumber                    [2]  LocationNumber OPTIONAL,
  cellGlobalIdOrServiceAreaIdOrLAI
				    [3]  CellGlobalIdOrServiceAreaIdOrLAI OPTIONAL,
  extensionContainer                [4]  ExtensionContainer OPTIONAL,
  ...,
  selectedLSA-Id                    [5]  LSAIdentity OPTIONAL,
  msc-Number                        [6]  ISDN-AddressString OPTIONAL,
  geodeticInformation               [7]  GeodeticInformation OPTIONAL,
  currentLocationRetrieved          [8]  NULL OPTIONAL,
  sai-Present                       [9]  NULL OPTIONAL
}

-- sai-Present indicates that the cellGlobalIdOrServiceAreaIdOrLAI parameter contains
-- a Service Area Identity.
-- currentLocationRetrieved shall be present 
-- if the location information were retrieved after a successfull paging.
LocationInformationGPRS ::= SEQUENCE {
  cellGlobalIdOrServiceAreaIdOrLAI
				    [0]  CellGlobalIdOrServiceAreaIdOrLAI OPTIONAL,
  routeingAreaIdentity              [1]  RAIdentity OPTIONAL,
  geographicalInformation           [2]  GeographicalInformation OPTIONAL,
  sgsn-Number                       [3]  ISDN-AddressString OPTIONAL,
  selectedLSAIdentity               [4]  LSAIdentity OPTIONAL,
  extensionContainer                [5]  ExtensionContainer OPTIONAL,
  ...,
  sai-Present                       [6]  NULL OPTIONAL,
  geodeticInformation               [7]  GeodeticInformation OPTIONAL,
  currentLocationRetrieved          [8]  NULL OPTIONAL,
  ageOfLocationInformation          [9]  AgeOfLocationInformation OPTIONAL
}

LSAIdentity ::= OCTET STRING(SIZE (3))

-- sai-Present indicates that the cellGlobalIdOrServiceAreaIdOrLAI parameter contains
-- a Service Area Identity.
-- currentLocationRetrieved shall be present if the location information
-- was retrieved after successful paging.
RAIdentity ::= OCTET STRING(SIZE (6))

-- Routing Area Identity is coded in accordance with 3GPP TS 29.060 [105].
-- It shall contain the value part defined in 3GPP TS 29.060 only. I.e. the 3GPP TS 29.060
-- type identifier octet shall not be included.
GeographicalInformation ::= OCTET STRING(SIZE (8))

--	Refers to geographical Information defined in 3GPP TS 23.032.
--	Only the description of an ellipsoid point with uncertainty circle
--	as specified in 3GPP TS 23.032 is allowed to be used
--	The internal structure according to 3GPP TS 23.032 is as follows:
--		Type of shape (ellipsoid point with uncertainty circle)	1 octet
--		Degrees of Latitude				3 octets
--		Degrees of Longitude				3 octets
--		Uncertainty code				1 octet
GeodeticInformation ::= OCTET STRING(SIZE (10))

--	Refers to Calling Geodetic Location defined in Q.763 (1999).
--	Only the description of an ellipsoid point with uncertainty circle
--	as specified in Q.763 (1999) is allowed to be used
--	The internal structure according to Q.763 (1999) is as follows:
--		Screening and presentation indicators		1 octet
--		Type of shape (ellipsoid point with uncertainty circle)	1 octet
--		Degrees of Latitude				3 octets
--		Degrees of Longitude				3 octets
--		Uncertainty code				1 octet
--		Confidence				1 octet
LocationNumber ::= OCTET STRING(SIZE (2..10))

-- This parameter carries the value part of the MS Classmark 2 IE defined in 
-- 3GPP TS 24.008 [35].
MS-Classmark2 ::= OCTET STRING(SIZE (3))

GPRSMSClass ::= SEQUENCE {
  mSNetworkCapability      [0]  MSNetworkCapability,
  mSRadioAccessCapability  [1]  MSRadioAccessCapability OPTIONAL}

-- This parameter carries the value part of the MS Network Capability IE defined in 
-- 3GPP TS 24.008 [35].
MSNetworkCapability ::= OCTET STRING(SIZE (1..8))

-- This parameter carries the value part of the MS Radio Access Capability IE defined in
-- 3GPP TS 24.008 [35].
MSRadioAccessCapability ::= OCTET STRING(SIZE (1..50))
      
END -- MAP-MS-DataTypes


-- 17.7.3	Call handling data types
MAP-CH-DataTypes {itu-t identified-organization(4) etsi(0) mobileDomain(0)
  gsm-Network(1) modules(3) map-CH-DataTypes(13) version8(8)}
DEFINITIONS IMPLICIT TAGS ::=
-- GVRoman's NOTE: 
-- this is reduced version of original module containing only types required for IN-Manager
BEGIN

CallReferenceNumber ::= OCTET STRING(SIZE (1..8))

END -- MAP-CH-DataTypes


-- 17.7.8	Common data types
MAP-CommonDataTypes {itu-t(0) identified-organization(4) etsi(0) mobileDomain(0)
  gsm-Network(1) modules(3) map-CommonDataTypes(18) version8(8)}
DEFINITIONS IMPLICIT TAGS ::=
-- GVRoman's NOTE: 
-- this is reduced version of original module containing only types required for IN-Manager
BEGIN

-- general data types
TBCD-STRING ::= OCTET STRING

-- This type (Telephony Binary Coded Decimal String) is used to
-- represent several digits from 0 through 9, *, #, a, b, c, two
-- digits per octet, each digit encoded 0000 to 1001 (0 to 9),
-- 1010 (*), 1011 (#), 1100 (a), 1101 (b) or 1110 (c); 1111 used
-- as filler when there is an odd number of digits.
-- bits 8765 of octet n encoding digit 2n
-- bits 4321 of octet n encoding digit 2(n-1) +1
IMSI ::= TBCD-STRING(SIZE (3..8))

-- the value represents the elapsed time in minutes since the last
-- network contact of the mobile station (i.e. the actuality of the
-- location information).
-- value "0" indicates that the MS is currently in contact with the
--           network
-- value "32767" indicates that the location information is at least
--               32767 minutes old
AgeOfLocationInformation ::= INTEGER(0..32767)

-- This type is used to represent a number for addressing
-- purposes. It is composed of
--	a)	one octet for nature of address, and numbering plan
--		indicator.
--	b)	digits of an address encoded as TBCD-String.
-- a)	The first octet includes a one bit extension indicator, a
--		3 bits nature of address indicator and a 4 bits numbering
--		plan indicator, encoded as follows:
-- bit 8: 1  (no extension)
-- bits 765: nature of address indicator
--	000  unknown
--	001  international number
--	010  national significant number
--	011  network specific number
--	100  subscriber number
--	101  reserved
--	110  abbreviated number
--	111  reserved for extension
-- bits 4321: numbering plan indicator
--	0000  unknown
--	0001  ISDN/Telephony Numbering Plan (Rec ITU-T E.164)
--	0010  spare
--	0011  data numbering plan (ITU-T Rec X.121)
--	0100  telex numbering plan (ITU-T Rec F.69)
--	0101  spare
--	0110  land mobile numbering plan (ITU-T Rec E.212)
--	0111  spare
--	1000  national numbering plan
--	1001  private numbering plan
--	1111  reserved for extension
--	all other values are reserved.
-- b)	The following octets representing digits of an address
--		encoded as a TBCD-STRING.
AddressString ::= OCTET STRING(SIZE (1..maxAddressLength))
maxAddressLength INTEGER ::= 20

-- This type is used to represent ISDN numbers.
ISDN-AddressString ::= AddressString(SIZE (1..maxISDN-AddressLength))
maxISDN-AddressLength INTEGER ::= 9

-- Refers to Cell Global Identification or Service Are Identification
-- defined in 3GPP TS 23.003.
-- The internal structure is defined as follows:
-- octet 1 bits 4321	Mobile Country Code 1st digit
--         bits 8765	Mobile Country Code 2nd digit
-- octet 2 bits 4321	Mobile Country Code 3rd digit
--         bits 8765	Mobile Network Code 3rd digit
--			or filler (1111) for 2 digit MNCs
-- octet 3 bits 4321	Mobile Network Code 1st digit
--         bits 8765	Mobile Network Code 2nd digit
-- octets 4 and 5	Location Area Code according to 3GPP TS 24.008
-- octets 6 and 7	Cell Identity (CI) value or 
-- 			Service Area Code (SAC) value 
--			according to 3GPP TS 23.003
CellGlobalIdOrServiceAreaIdOrLAI ::= CHOICE {
    cellGlobalIdOrServiceAreaIdFixedLength
				[0]	CellGlobalIdOrServiceAreaIdFixedLength,
    laiFixedLength		[1]	LAIFixedLength
}

CellGlobalIdOrServiceAreaIdFixedLength ::= OCTET STRING(SIZE (7))


-- Refers to Location Area Identification defined in TS 3GPP TS 23.003 [17].
-- The internal structure is defined as follows:
-- octet 1 bits 4321	Mobile Country Code 1st digit
--         bits 8765	Mobile Country Code 2nd digit
-- octet 2 bits 4321	Mobile Country Code 3rd digit
--         bits 8765	Mobile Network Code 3rd digit
--			or filler (1111) for 2 digit MNCs
-- octet 3 bits 4321	Mobile Network Code 1st digit
--         bits 8765	Mobile Network Code 2nd digit
-- octets 4 and 5	Location Area Code according to TS 3GPP TS 24.008 [35]
-- data types for subscriber management
LAIFixedLength ::= OCTET STRING(SIZE (5))


--	Refers to International Mobile Station Equipment Identity
--	and Software Version Number (SVN) defined in TS 3GPP TS 23.003 [17].
--	If the SVN is not present the last octet shall contain the
--	digit 0 and a filler.
--	If present the SVN shall be included in the last octet.
IMEI ::= TBCD-STRING(SIZE (8))


END -- MAP-CommonDataTypes

-- 17.7.11	Extension data types
MAP-ExtensionDataTypes {itu-t(0) identified-organization(4) etsi(0)
  mobileDomain(0) gsm-Network(1) modules(3) map-ExtensionDataTypes(21)
  version8(8)} 
DEFINITIONS IMPLICIT TAGS ::=
-- GVRoman's NOTE: 
-- this is reduced version of original module containing only types required for IN-Manager
BEGIN

EXPORTS PrivateExtension, ExtensionContainer;

-- IOC for private MAP extensions
/*
MAP-EXTENSION ::= CLASS {
    &ExtensionType	OPTIONAL,
    &extensionId	OBJECT IDENTIFIER
}
*/
-- The length of the Object Identifier shall not exceed 16 octets and the
-- number of components of the Object Identifier shall not exceed 16
-- data types
ExtensionContainer ::= SEQUENCE {
    privateExtensionList	[0]	PrivateExtensionList OPTIONAL,
    pcs-Extensions		[1]	PCS-Extensions OPTIONAL,
  ...
}

PrivateExtensionList ::= SEQUENCE SIZE (1..maxNumOfPrivateExtensions)
				OF PrivateExtension

PrivateExtension ::= SEQUENCE {
/* GVR: original definition was:
    extId    MAP-EXTENSION.&extensionId({ExtensionSet}),
    extType  MAP-EXTENSION.&ExtensionType({ExtensionSet}{@extId}) OPTIONAL
 */
    extId	OBJECT IDENTIFIER,
    ... -- GVR: just skip the rest while decoding
}

maxNumOfPrivateExtensions INTEGER ::= 10

-- ExtensionSet MAP-EXTENSION ::= {
--    ...
    -- ExtensionSet is the set of all defined private extensions--
-- }

-- Unsupported private extensions shall be discarded if received.
PCS-Extensions ::= SEQUENCE {...}

END -- MAP-ExtensionDataTypes


-- ******************************************************************* --
-- CAP modules follow
-- ******************************************************************* --


-- 5	Common CAP Types
-- 5.1	Data types
CAP-datatypes {itu-t(0) identified-organization(4) etsi(0) mobileDomain(0)
  umts-network(1) modules(3) cap-datatypes(52) version4(3)} 
DEFINITIONS IMPLICIT TAGS ::=
-- GVRoman's NOTE: 
-- this is reduced version of original module containing only types required for IN-Manager
BEGIN
IMPORTS
  cap-classes, in-CS2-datatypes, map-CommonDataTypes
    FROM IN-Maneger-OIDs
  Integer4
    FROM CS1-DataTypes {itu-t(0) identified-organization(4) etsi(0) inDomain(1)
      in-network(1) modules(0) cs1-datatypes(2) version1(0)}
  CriticalityType
    FROM IN-CS2-datatypes {itu-t(0) identified-organization(4) etsi(0) inDomain(1)
      in-network(1) cs2(20) modules(0) in-cs2-datatypes(0) version1(0)}
  AddressString
    FROM MAP-CommonDataTypes {itu-t(0) identified-organization(4) etsi(0)
      mobileDomain(0) gsm-Network(1) modules(3) map-CommonDataTypes(18)
      version8(8)}
  Code
    FROM Remote-Operations-Information-Objects
    { joint-iso-itu-t remote-operations(4) informationObjects(5) version1(0) }
    -- ros-InformationObjects
/* GVR:    
  EXTENSION, SupportedExtensions
    FROM CAP-classes { itu-t(0) identified-organization(4) etsi(0) mobileDomain(0)
      umts-network(1) modules(3) cap-classes(54) version4(3) }
*/      
    -- cap-classes
    ;


-- An SMS-AddressString may contain an alphanumeric character string. In this 
-- case, a nature of address indicator '101'B is used, in accordance with 
-- 3GPP TS 23.040 [6]. The address is coded in accordance with the GSM 7-bit 
-- default alphabet definition and the SMS packing rules as specified in 
-- 3GPP TS 23.038 [15] in this case.

SMS-AddressString ::= AddressString(SIZE (1..maxSMS-AddressStringLength))
maxSMS-AddressStringLength INTEGER ::= 11


SMSEvent ::= SEQUENCE {
    eventTypeSMS	[0]	EventTypeSMS,
    monitorMode		[1]	MonitorMode
}

-- Values sms-CollectedInfo and sms-DeliveryRequested may be used for TDPs only.
EventTypeSMS ::= ENUMERATED {
    sms-CollectedInfo(1), o-smsFailure(2), o-smsSubmission(3),
    sms-DeliveryRequested(11), t-smsFailure(12), t-smsDelivery(13)
}

-- Indicates the event is relayed and/or processed by the SSP.
-- Transparent means that the gsmSSF or gprsSSF does not notify the gsmSCF of the event.
-- For the use of this parameter refer to the procedure descriptions in clause 11.
-- For the RequestNotificationCharging operation, 'interrupted' shall not be used in MonitorMode.
MonitorMode ::= ENUMERATED {
  interrupted(0), notifyAndContinue(1), transparent(2)}

-- MO SMS error values which are reported to gsmSCF.
-- Most of these values are received from the SMSC as a response to
-- MO-ForwardSM operation.
MO-SMSCause ::= ENUMERATED {
  systemFailure(0), unexpectedDataValue(1), facilityNotSupported(2),
  sM-DeliveryFailure(3), releaseFromRadioInterface(4)}

-- This variable is sent to the gsmSCF for a Short Message delivery failure
-- notification.
-- If the delivery failure is due to RP-ERROR RPDU received from the MS,
-- then MT-SMSCause shall be set to the RP-Cause component in the RP-ERROR RPDU.
-- Refer to 3G TS 24.011 [10] for the encoding of RP-Cause values.
-- Otherwise, if the delivery failure is due to internal failure in the MSC or SGSN
-- or time-out from the MS, then MT-SMSCause shall be set to 'Protocol error,
-- unspecified', as defined in 3G TS 24.011 [10].
MT-SMSCause ::= OCTET STRING(SIZE (1))

-- RP cause according to 3GPP TS 24.011 [10] or 3GPP TS 29.002 [11].
-- GsmSCF shall send this cause in the ReleaseSMS operation.
-- For a MO-SMS service, the MSC or SGSN shall send the RP Cause to the originating MS.
-- It shall be used to overwrite the RP-Cause element in the RP-ERROR RPDU.
-- For a MT-SMS service, the MSC or SGSN shall send the RP Cause to the sending SMS-GMSC.
-- It shall be used to overwrite the RP-Cause element in the RP-ERROR RPDU.
RPCause ::= OCTET STRING (SIZE (1))

-- Indicates the Called Party Number, including service selection information.
-- Refer to 3GPP TS 24.008 [9] for encoding.
-- This data type carries only the 'type of number', 'numbering plan
-- identification' and 'number digit' fields defined in 3GPP TS 24.008 [9];
-- it does not carry the 'called party BCD number IEI' or 'length of called
-- party BCD number contents'.
-- In the context of the DestinationSubscriberNumber field in ConnectSMSArg or 
-- InitialDPSMSArg, a CalledPartyBCDNumber may also contain an alphanumeric 
-- character string. In this case, type-of-number '101'B is used, in accordance 
-- with 3GPP TS 23.040 [6]. The address is coded in accordance with the 
-- GSM 7-bit default alphabet definition and the SMS packing rules 
-- as specified in 3GPP TS 23.038 [15] in this case.
CalledPartyBCDNumber ::= OCTET STRING (SIZE (capMinCalledPartyBCDNumberLength ..
						capMaxCalledPartyBCDNumberLength))

capMinCalledPartyBCDNumberLength INTEGER ::= 1
capMaxCalledPartyBCDNumberLength INTEGER ::= 41


--  Indicates the time and timezone, relative to GMT. This parameter is BCD encoded.
--  The year digit indicating millenium occupies bits 0-3 of the first octet, and the year
--  digit indicating century occupies bits 4-7 of the first octet.
--  The year digit indicating decade occupies bits 0-3 of the second octet, whilst the digit
--  indicating the year within the decade occupies bits 4-7 of the second octet.
--  The most significant month digit occupies bits 0-3 of the third octet, and the least
--  significant month digit occupies bits 4-7 of the third octet.
--  The most significant day digit occupies bits 0-3 of the fourth octet, and the least
--  significant day digit occupies bits 4-7 of the fourth octet.
--  The most significant hours digit occupies bits 0-3 of the fifth octet, and the least
--  significant hours digit occupies bits 4-7 of the fifth octet.
--  The most significant minutes digit occupies bits 0-3 of the sixth octet, and the least
--  significant minutes digit occupies bits 4-7 of the sixth octet.
--  The most significant seconds digit occupies bits 0-3 of the seventh octet, and the least
--  significant seconds digit occupies bits 4-7 of the seventh octet.
--
--  The timezone information occupies the eighth octet. For the encoding of Timezone refer to
--  3GPP TS 23.040 [6].
--
--  The BCD digits are packed and encoded as follows:
--
--  Bit	 7  6  5   4  |  3  2  1  0
--       2nd digit    | 1st digit          Octet 1
--       3rd digit    | 4th digit          Octet 2
--           	         ..                   ..
--       nth digit    | n-1th digit        Octet m
--
--       0000		digit 0
--       0001		digit 1
--       0010		digit 2
--       0011		digit 3
--       0100		digit 4
--       0101		digit 5
--       0110		digit 6
--       0111		digit 7
--       1000		digit 8
--       1001		digit 9
--       1010		spare
--       1011		spare
--       1100		spare
--       1101		spare
--       1110		spare
--       1101		spare
--
-- where the leftmost bit of the digit is either bit 7 or bit 3 of the octet.
TimeAndTimezone ::= OCTET STRING (SIZE (capMinTimeAndTimezoneLength .. 
					capMaxTimeAndTimezoneLength))

capMinTimeAndTimezoneLength INTEGER ::= 8
capMaxTimeAndTimezoneLength INTEGER ::= 8


-- This parameter indicates an extension of an argument data type.
-- Its content is network operator specific
capNumOfExtensions INTEGER ::= 10
Extensions ::= SEQUENCE SIZE (1..capNumOfExtensions) OF ExtensionField

ExtensionField ::= SEQUENCE {
/* GVR: original definition was:
  type         EXTENSION.&id({SupportedExtensions}),
  -- shall identify the value of an EXTENSION type
  criticality  CriticalityType DEFAULT ignore,
  value        [1]  EXTENSION.&ExtensionType({SupportedExtensions}{@type}),
  ...
*/
  type         Code,
  -- shall identify the value of an EXTENSION type
  criticality  CriticalityType DEFAULT ignore,
  -- GVR:  implicit tagging is in use, so just use the OCTET STRING  instead of OpenType
  value        [1]  OCTET STRING, 
  ...
}


EventSpecificInformationSMS ::= CHOICE {
    o-smsFailureSpecificInfo	[0]	SEQUENCE {
	failureCause  [0]  MO-SMSCause OPTIONAL,
	...
    },
    o-smsSubmissionSpecificInfo	[1]	SEQUENCE {
    -- no specific info defined -- ...
    },
    t-smsFailureSpecificInfo	[2]	SEQUENCE {
	failureCause  [0]  MT-SMSCause OPTIONAL,
	...
    },
    t-smsDeliverySpecificInfo	[3]	SEQUENCE {
	-- no specific info defined -- ...
    }
}

-- TP Data Coding Scheme according to 3GPP TS 23.040 [6]
TPDataCodingScheme ::= OCTET STRING(SIZE (1))

-- indicates the protocol used above the SM-Transfer Layer as specified in 3GPP TS 23.040 [6].
TPProtocolIdentifier ::= OCTET STRING(SIZE (1))

-- contains the 1st octect of the applicable TPDU or the SMS-COMMAND TPDU as specified in
-- 3GPP TS 23.040 [6].
TPShortMessageSpecificInfo ::= OCTET STRING(SIZE (1))

-- indicates the length of the validity period or the absolute time of the validity
-- period termination as specified in 3GPP TS 23.040 [6].
-- the length of ValidityPeriod is either 1 octet or 7 octets
TPValidityPeriod ::= OCTET STRING(SIZE (1..7))

-- This parameter indicates the SMS billing and/or charging characteristics.
-- The violation of the UserDefinedConstraint shall be handled as an ASN.1 syntax error.
FCISMSBillingChargingCharacteristics ::= OCTET STRING (SIZE
					(capMinFCIBillingChargingLength ..
					    capMaxFCIBillingChargingLength))
	(CONSTRAINED BY {-- shall be the result of the BER-encoded value of type -
	    CAMEL-FCISMSBillingChargingCharacteristics})

capMinFCIBillingChargingLength INTEGER ::= 5
capMaxFCIBillingChargingLength INTEGER ::= 225

CAMEL-FCISMSBillingChargingCharacteristics ::= CHOICE {
    fCIBCCCAMELsequence1	[0] SEQUENCE {
	freeFormatData			[0] OCTET STRING (SIZE
					    (capMinFCIBillingChargingDataLength ..
						capMaxFCIBillingChargingDataLength)),
	appendFreeFormatData		[1] AppendFreeFormatData DEFAULT overwrite
    }
}
capMinFCIBillingChargingDataLength INTEGER ::= 1
capMaxFCIBillingChargingDataLength INTEGER ::= 160

AppendFreeFormatData ::= ENUMERATED { overwrite (0), append (1) }

-- Indicates the timer to be reset.
TimerID ::= ENUMERATED { tssf (0) }

-- Indicates the timer value (in seconds).
TimerValue ::= Integer4

END -- CAP-datatypes


-- GVRoman's NOTE: This module is excluded in order to satisfy asn1c of SourceForge
-- 5.5	Classes
/*
CAP-classes {itu-t(0) identified-organization(4) etsi(0) mobileDomain(0)
  umts-network(1) modules(3) cap-classes(54) version4(3)}
DEFINITIONS ::=
-- GVRoman's NOTE: 
-- this is reduced version of original module containing only types required for IN-Manager
BEGIN

IMPORTS
  ros-InformationObjects, in-CS2-datatypes
    FROM IN-Maneger-OIDs
  Code
    FROM Remote-Operations-Information-Objects
    { joint-iso-itu-t remote-operations(4) informationObjects(5) version1(0) }
    -- ros-InformationObjects
  CriticalityType
    FROM IN-CS2-datatypes {itu-t(0) identified-organization(4) etsi(0) inDomain(1)
      in-network(1) cs2(20) modules(0) in-cs2-datatypes(0) version1(0)}
    ;


EXTENSION ::= CLASS {
  &ExtensionType	,
  &criticality		CriticalityType DEFAULT ignore,
  &id			Code
} WITH SYNTAX {
  EXTENSION-SYNTAX	&ExtensionType
  CRITICALITY		&criticality
  IDENTIFIED BY		&id
}

-- Only value Global OBJECT IDENTIFIER is used for &id;
-- Only the value ignore (0) is used for &criticality.
-- Example of addition of an extension named 'Some Network Specific Indicator' of type
-- BOOLEAN, with criticality 'ignore' and identified by global Object Identifier.
--
-- Example of definition using the above information object class:
--
-- SomeNetworkSpecificIndicator EXTENSION ::= {
-- 	EXTENSION-SYNTAX	BOOLEAN
--	CRITICALITY			ignore
--	IDENTIFIED BY		global : {itu-t(0) identified-organization(4) organisation(0) gsm(1)
--								 capextension(2)}
--	}
-- Example of transfer syntax, using the ExtensionField datatype as specified in clause 5.
-- Assuming the value of the extension is set to TRUE, the extensions parameter becomes
-- a Sequence of type {itu-t(0) identified-organization(4) organisation(0) gsm(1)
-- capextension(2)}, criticality ENUMERATED ::= ignore(0) and value [1] EXPLICIT BOOLEAN
-- ::= TRUE.
--
-- Use of ITU-T Recommendation Q.1400 [52] defined Extension is for further study.
-- In addition the extension mechanism marker is used to identify the future minor additions
-- to CAP.
firstExtension EXTENSION ::= {
  EXTENSION-SYNTAX	NULL
  CRITICALITY		ignore
  IDENTIFIED BY		global:
      {itu-t(0) identified-organization(4) organisation(0) gsm(1) capextension(2)}
}

-- firstExtension is just an example.
SupportedExtensions EXTENSION ::=
  { firstExtension, ... -- full set of network operator extensions -- }


END -- CAP-classes
*/

-- ******************************************************************* --
-- IN-Manager modules follow
-- ******************************************************************* --

IN-Manager-CAP-errors
-- CAP errors utilized by IN-Manager,
-- taken from CAP-errortypes cap-errortypes;
DEFINITIONS IMPLICIT TAGS ::=
BEGIN

IMPORTS
  ros-InformationObjects
    FROM IN-Maneger-OIDs
  Code, ERROR
    FROM Remote-Operations-Information-Objects
    { joint-iso-itu-t remote-operations(4) informationObjects(5) version1(0) }
    -- ros-InformationObjects
    ;

-- Basic errors for SMS operations
IN-SMSErrors ERROR ::= {
    missingParameter | taskRefused | unexpectedComponentSequence |
    unexpectedDataValue | unexpectedParameter
}
-- Errors for RequestReportSMSEvent operation
IN-SMSEventErrors ERROR ::= {
	parameterOutOfRange | systemFailure | IN-SMSErrors
}

-- Errors for InitialDPSMS operation
IN-IniDPSMSEventErrors ERROR ::= {
	missingCustomerRecord | IN-SMSEventErrors
}

-- Errors for ResetTimerSMS operation
IN-SMSTimerErrors ERROR ::= {
    parameterOutOfRange | IN-SMSErrors
}

-- The caller response was not as expected.
missingCustomerRecord ERROR ::= {CODE  errcode-missingCustomerRecord}

-- The Service Logic Program could not be found in the gsmSCF.
missingParameter ERROR ::= {CODE  errcode-missingParameter}

-- An expected optional parameter was not received.
parameterOutOfRange ERROR ::= {CODE  errcode-parameterOutOfRange}

-- The requested information cannot be found.
systemFailure ERROR ::= {
  PARAMETER  UnavailableNetworkResource
  CODE       errcode-systemFailure 
}

UnavailableNetworkResource ::= ENUMERATED {
  unavailableResources(0), componentFailure(1),
  basicCallProcessingException(2), resourceStatusFailure(3), endUserFailure(4)
}

-- The operation could not be completed due to a system failure at the serving physical entity.
taskRefused ERROR ::= {
  PARAMETER  ENUMERATED {generic(0), unobtainable(1), congestion(2)}
  CODE       errcode-taskRefused
}

-- A requested resource is not available at the serving entity.
unexpectedComponentSequence ERROR ::= { CODE  errcode-unexpectedComponentSequence }

-- An incorrect sequence of Components was received (e.g. 'DisconnectForwardConnection'
-- followed by 'PlayAnnouncement').
unexpectedDataValue ERROR ::= { CODE  errcode-unexpectedDataValue }

-- The data value was not as expected (e.g. route number expected but billing number received)
unexpectedParameter ERROR ::= { CODE  errcode-unexpectedParameter }

--
-- Error codes from CAP-errorcodes cap-errorcodes;
--

errcode-missingCustomerRecord	Code ::= local:6

errcode-missingParameter	Code ::= local:7

errcode-parameterOutOfRange	Code ::= local:8

errcode-systemFailure		Code ::= local:11

errcode-taskRefused		Code ::= local:12

errcode-unexpectedComponentSequence Code ::= local:14

errcode-unexpectedDataValue	Code ::= local:15

errcode-unexpectedParameter	Code ::= local:16

END -- IN-Manager-CAP-errors



IN-Manager-Operations
-- This is a mofified variant of operations and arguments from cap4SMS CONTRACT
-- (dialogue initiated by gprsSSF or gsmSSF with InitialDPSMS Operation)
-- 7	SMS Control
-- 7.1	SMS operations and arguments
-- CAP-SMS-ops-args {itu-t(0) identified-organization(4) etsi(0) mobileDomain(0) umts-network(1) modules(3) cap-SMS-ops-args(105) version5(4)}
DEFINITIONS IMPLICIT TAGS ::=
-- GVRoman's NOTE: This module is for informative purposes only. 
-- SourceForge's asn1c doesn't produce something usefull from these definitions.
BEGIN

IMPORTS
  ros-InformationObjects
    FROM IN-Maneger-OIDs
  Code, OPERATION
    FROM Remote-Operations-Information-Objects
    { joint-iso-itu-t remote-operations(4) informationObjects(5) version1(0) }
    -- ros-InformationObjects
  IN-IniDPSMSEventErrors, IN-SMSErrors, IN-SMSEventErrors, IN-SMSTimerErrors
    FROM IN-Manager-CAP-errors
  InitialDPSMSArg, ConnectSMSArg, ReleaseSMSArg, RequestReportSMSEventArg,
  EventReportSMSArg, ResetTimerSMSArg, FurnishChargingInformationSMSArg
    FROM IN-Manager-Operations-Args;

-- Sms Activation Package
opcode-initialDPSMS			Code ::= local:60
-- Sms Billing Package
opcode-furnishChargingInformationSMS	Code ::= local: 61
-- Sms Connect Package
opcode-connectSMS			Code ::= local: 62
-- Sms Event Handling Package
opcode-requestReportSMSEvent		Code ::= local:63
opcode-eventReportSMS			Code ::= local:64
-- Sms Processing Package
opcode-continueSMS			Code ::= local:65
-- Sms Release Package	
opcode-releaseSMS			Code ::= local: 66
-- Sms Timer Package
opcode-resetTimerSMS			Code ::= local: 67

-- ************************************************************ --
-- cap3SMS and cap4SMS CONTRACTs conclude following operations: --
-- ************************************************************ --
--	SmsInvokable operations:
SmsInvokable OPERATION ::= {
    initialDPSMS | connectSMS |
    requestReportSMSEvent | eventReportSMS |
    furnishChargingInformationSMS | resetTimerSMS
}
--	SmsReturnable operations:
SmsReturnable OPERATION ::= {
    initialDPSMS | connectSMS | continueSMS | releaseSMS |
    requestReportSMSEvent |
    furnishChargingInformationSMS | resetTimerSMS
}

--  Direction: gsmSSF or gprsSSF -> gsmSCF, Timer: Tidpsms
--  This operation is used after a TDP to indicate request for service.
initialDPSMS OPERATION ::= {
    ARGUMENT		InitialDPSMSArg
    RETURN RESULT	FALSE
    ERRORS		{ IN-IniDPSMSEventErrors }
    CODE		opcode-initialDPSMS
}

--  Direction: gsmSCF -> gsmSSF or gprsSSF, Timer: Tconsms
--  This operation is used to request the smsSSF to perform the SMS processing
--  actions to route or forward a short message to a specified destination.
connectSMS OPERATION ::= {
    ARGUMENT		ConnectSMSArg
    RETURN RESULT	FALSE
    ERRORS		{ IN-SMSEventErrors }
    CODE		opcode-connectSMS
}

-- Direction: gsmSCF -> smsSSF, Timer: Tcuesms 
-- This operation is used to request the smsSSF to proceed with
-- Short Message processing at the DP at which it previously suspended
-- Short Message processing to await gsmSCF instructions (i.e. proceed
-- to the next Point in Association in the SMS FSM). The smsSSF
-- continues SMS processing without substituting new data from the gsmSCF.
continueSMS OPERATION ::= {
    RETURN RESULT	FALSE
    ALWAYS RESPONDS	FALSE
    CODE		opcode-continueSMS
}

--  Direction: gsmSCF -> gsmSSF or gprsSSF, Timer: Trelsms
--  This operation is used to prevent an attempt to submit or deliver a short message. 
releaseSMS OPERATION ::= {
    ARGUMENT		ReleaseSMSArg
    RETURN RESULT	FALSE
    ALWAYS RESPONDS	FALSE
    CODE		opcode-releaseSMS
}

--  Direction: gsmSCF -> gsmSSF or gprsSSF, Timer: Trrbsms
--  This operation is used to request the gsmSSF or gprsSSF to monitor for a
--  Short Message related event (FSM events such as submission, delivery or failure)
--  and to send a notification to the gsmSCF when the event is detected.
requestReportSMSEvent OPERATION ::= {
    ARGUMENT		RequestReportSMSEventArg
    RETURN RESULT	FALSE
    ERRORS		{ IN-SMSEventErrors }
    CODE		opcode-requestReportSMSEvent
}

--  Direction: gsmSSF or gprsSSF -> gsmSCF, Timer: Terbsms
--  This operation is used to notify the gsmSCF of a Short Message related event (FSM events
--  such as submission, delivery or failure) previously requested by the gsmSCF in a
--  RequestReportSMSEvent operation.
eventReportSMS OPERATION ::= {
  ARGUMENT		EventReportSMSArg
  RETURN RESULT		FALSE
  ALWAYS RESPONDS	FALSE
  CODE			opcode-eventReportSMS
}

--  Direction: gsmSCF ?? gsmSSF or gprsSSF, Timer: Tfcisms 
--  This operation is used to request the smsSSF to generate, register a charging record
--  or to include some information in the default SM record. The registered charging record is
--  intended for off line charging of the Short Message.
furnishChargingInformationSMS OPERATION ::= {
    ARGUMENT		FurnishChargingInformationSMSArg
    RETURN RESULT	FALSE
    ERRORS		{ IN-SMSErrors }
    CODE		opcode-furnishChargingInformationSMS
}

-- Direction: gsmSCF -> smsSSF, Timer: Trtsms 
-- This operation is used to request the smsSSF to refresh an application
-- timer in the smsSSF.
resetTimerSMS OPERATION ::= {
    ARGUMENT		ResetTimerSMSArg
    RETURN RESULT	FALSE
    ERRORS		{ IN-SMSTimerErrors }
    CODE		opcode-resetTimerSMS
}

END -- IN-Manager-Operations


IN-Manager-Operations-Args
DEFINITIONS IMPLICIT TAGS ::=
-- GVRoman's NOTE: This module is the main one. It contains definitions for
-- types transferred as components in component portion of TCAP message.
BEGIN

IMPORTS
  cs1-DataTypes, in-CS2-datatypes, cap-datatypes, 
  map-CH-DataTypes, map-MS-DataTypes, map-CommonDataTypes, map-Ext-DataTypes
    FROM IN-Maneger-OIDs
  ServiceKey
    FROM CS1-DataTypes  -- cs1-DataTypes
  MiscCallInfo
    FROM IN-CS2-datatypes -- in-CS2-datatypes
  IMEI, IMSI, ISDN-AddressString
    FROM MAP-CommonDataTypes -- map-CommonDataTypes
  CallReferenceNumber
    FROM MAP-CH-DataTypes -- map-CH-DataTypes
  GPRSMSClass, LocationInformation, LocationInformationGPRS, MS-Classmark2
    FROM MAP-MS-DataTypes -- map-MS-DataTypes
  ExtensionContainer
    FROM MAP-ExtensionDataTypes -- map-Ext-DataTypes
  CalledPartyBCDNumber, Extensions, EventSpecificInformationSMS, EventTypeSMS, 
  FCISMSBillingChargingCharacteristics, RPCause, SMSEvent, SMS-AddressString,
  TimeAndTimezone, TimerID, TimerValue, TPValidityPeriod, TPDataCodingScheme,
  TPProtocolIdentifier, TPShortMessageSpecificInfo
    FROM CAP-datatypes -- cap-datatypes
    ;

--  Direction: gsmSSF or gprsSSF -> gsmSCF, Timer: Tidpsms
--  This operation is used after a TDP to indicate request for service.
InitialDPSMSArg ::= SEQUENCE {
  serviceKey                   [0]  ServiceKey,
  destinationSubscriberNumber  [1]  CalledPartyBCDNumber OPTIONAL,
  callingPartyNumber           [2]  SMS-AddressString OPTIONAL,
  eventTypeSMS                 [3]  EventTypeSMS OPTIONAL,
  iMSI                         [4]  IMSI OPTIONAL,
  locationInformationMSC       [5]  LocationInformation OPTIONAL,
  locationInformationGPRS      [6]  LocationInformationGPRS OPTIONAL,
  sMSCAddress                  [7]  ISDN-AddressString OPTIONAL,
  timeAndTimezone              [8]  TimeAndTimezone OPTIONAL,
  tPShortMessageSpecificInfo   [9]  TPShortMessageSpecificInfo OPTIONAL,
  tPProtocolIdentifier         [10]  TPProtocolIdentifier OPTIONAL,
  tPDataCodingScheme           [11]  TPDataCodingScheme OPTIONAL,
  tPValidityPeriod             [12]  TPValidityPeriod OPTIONAL,
  extensions                   [13]  Extensions OPTIONAL,
  ...,
  smsReferenceNumber           [14]  CallReferenceNumber OPTIONAL,
  mscAddress                   [15]  ISDN-AddressString OPTIONAL,
  sgsn-Number                  [16]  ISDN-AddressString OPTIONAL,
  ms-Classmark2                [17]  MS-Classmark2 OPTIONAL,
  gPRSMSClass                  [18]  GPRSMSClass OPTIONAL,
  iMEI                         [19]  IMEI OPTIONAL,
  calledPartyNumber            [20]  ISDN-AddressString OPTIONAL
}

--  Direction: gsmSCF -> gsmSSF or gprsSSF, Timer: Tconsms
--  This operation is used to request the smsSSF to perform the SMS processing
--  actions to route or forward a short message to a specified destination.
ConnectSMSArg ::= SEQUENCE {
    callingPartysNumber			[0]  SMS-AddressString		OPTIONAL,
    destinationSubscriberNumber		[1]  CalledPartyBCDNumber	OPTIONAL,
    sMSCAddress				[2]  ISDN-AddressString		OPTIONAL,
    extensions				[10] Extensions			OPTIONAL,
    ...
}

--  Direction: gsmSCF -> gsmSSF or gprsSSF, Timer: Trelsms
--  This operation is used to prevent an attempt to submit or deliver a short message. 
ReleaseSMSArg ::= RPCause

--  Direction: gsmSSF or gprsSSF -> gsmSCF, Timer: Terbsms
--  This operation is used to notify the gsmSCF of a Short Message related event (FSM events
--  such as submission, delivery or failure) previously requested by the gsmSCF in a
--  RequestReportSMSEvent operation.
EventReportSMSArg ::= SEQUENCE {
    eventTypeSMS		[0]	EventTypeSMS,
    eventSpecificInformationSMS	[1]	EventSpecificInformationSMS OPTIONAL,
    miscCallInfo		[2]	MiscCallInfo DEFAULT {messageType request},
    extensions			[10]	Extensions OPTIONAL,
    ...
}

--  Direction: gsmSCF -> gsmSSF or gprsSSF, Timer: Trrbsms
--  This operation is used to request the gsmSSF or gprsSSF to monitor for a
--  Short Message related event (FSM events such as submission, delivery or failure)
--  and to send a notification to the gsmSCF when the event is detected.
RequestReportSMSEventArg ::= SEQUENCE {
    sMSEvents	[0]	SEQUENCE (SIZE (1 .. capNumOfSMSEvents)) OF SMSEvent,
    extensions	[10]	Extensions OPTIONAL,
    ...
}
capNumOfSMSEvents INTEGER ::= 10

--  Direction: gsmSCF ?? gsmSSF or gprsSSF, Timer: Tfcisms 
--  This operation is used to request the smsSSF to generate, register a charging record
--  or to include some information in the default SM record. The registered charging record is
--  intended for off line charging of the Short Message.
FurnishChargingInformationSMSArg ::= FCISMSBillingChargingCharacteristics

-- Direction: gsmSCF -> smsSSF, Timer: Trtsms 
-- This operation is used to request the smsSSF to refresh an application
-- timer in the smsSSF.
ResetTimerSMSArg ::= SEQUENCE {
    timerID		[0] TimerID	DEFAULT tssf,
    timervalue		[1] TimerValue,
    extensions		[2] Extensions	OPTIONAL,
    ...
}


END -- IN-Manager-Operations-Args

/*
-- Sample values for arguments of some operations
IN-Manager-Operations-Values
DEFINITIONS IMPLICIT TAGS ::=
BEGIN

IMPORTS
  InitialDPSMSArg, EventReportSMSArg, RequestReportSMSEventArg
    FROM IN-Manager-Operations-Args;


cmd1-InitialDPSMS InitialDPSMSArg ::= {
  serviceKey			11,
  destinationSubscriberNumber	'91131133'H
  callingPartyNumber		'9179139163393f'H,
  eventTypeSMS			sms-CollectedInfo, -- 1 --
  iMSI				'250013901388780f'H,
  locationInformationMSC	{
    vlr-number			'9179139860001f'H,
    locationNumber		'810179139860001f'H,
    cellGlobalIdOrServiceAreaIdOrLAI cellGlobalIdOrServiceAreaIdFixedLength :
				'250f1097FE1389'H,
  },
  sMSCAddress			'9179029869990f'H,
  timeAndTimezone		'2005042215032642'H,
  tPShortMessageSpecificInfo	'11'H,
  tPProtocolIdentifier		'00'H,
  tPDataCodingScheme		'08'H,
  tPValidityPeriod		'da'H
}


cmd2-RequestReportSMSEvent RequestReportSMSEventArg ::= {
    sMSEvents	{
	{ eventTypeSMS	o-smsFailure -- 2 --,
	  monitorMode	notifyAndContinue -- 1--  
	},
	{ eventTypeSMS	o-smsSubmission -- 3 --,
	  monitorMode	notifyAndContinue -- 1--  
	}
    }
}

cmd4-EventReportSMS EventReportSMSArg ::= { 
    eventTypeSMS	o-smsSubmission -- 3 --,
    miscCallInfo	notification -- 1 --
}
END    

*/
