/* $Id$ */
/* ************************************************************************** *
 * Module: MAP Supplementary service data types.                              *
 * -- 3GPP TS 29.002 V7.2.0 (2005-12)					      *
 * ************************************************************************** *
 * Author: R.V. Gerasimov                                                     *
 * ************************************************************************** */

-- 17.7.4	Supplementary service data types
MAP-SS-DataTypes {
   itu-t(0) identified-organization (4) etsi (0) mobileDomain (0)
   gsm-Network (1) modules (3) map-SS-DataTypes (14) version10 (10)}
DEFINITIONS IMPLICIT TAGS ::= BEGIN
EXPORTS
    SS-Status,
    SS-ForBS-Code,
    USSD-Arg,
    USSD-Res, 
    USSD-DataCodingScheme,
    USSD-String,
    Password,
    SS-List,
    ForwardingOptions
;
IMPORTS
    ISDN-AddressString,
    BasicServiceCode,
    AlertingPattern
FROM MAP-CommonDataTypes {
   itu-t(0) identified-organization (4) etsi (0) mobileDomain (0)
   gsm-Network (1) modules (3) map-CommonDataTypes (18) version10 (10)}

    SS-Code
FROM MAP-SS-Code {
   itu-t(0) identified-organization (4) etsi (0) mobileDomain (0)
   gsm-Network (1) modules (3) map-SS-Code (15) version10 (10)}
;

SS-Status ::= OCTET STRING (SIZE (1))
-- bits 8765: 0000 (unused)
-- bits 4321: Used to convey the "P bit","R bit","A bit" and "Q bit",
--		    representing supplementary service state information
--		    as defined in TS 3GPP TS 23.011 [22]
-- bit 4: "Q bit"
-- bit 3: "P bit"
-- bit 2: "R bit"
-- bit 1: "A bit"

ForwardingOptions ::= OCTET STRING (SIZE (1))
-- bit 8: notification to forwarding party
--	0  no notification
--	1  notification
-- bit 7: redirecting presentation
--	0 no presentation  
--	1  presentation
-- bit 6: notification to calling party
--	0  no notification
--	1  notification
-- bit 5: 0 (unused)
-- bits 43: forwarding reason
--	00  ms not reachable
--	01  ms busy
--	10  no reply
--	11  unconditional when used in a SRI Result, 
--	    or call deflection when used in a RCH Argument
-- bits 21: 00 (unused)

SS-ForBS-Code ::= SEQUENCE {
    ss-Code		SS-Code,
    basicService	BasicServiceCode	OPTIONAL,
    ...,
    longFTN-Supported	[4] NULL		OPTIONAL
}

USSD-Arg ::= SEQUENCE {
    ussd-DataCodingScheme	USSD-DataCodingScheme,
    ussd-String			USSD-String,
    ... ,
    alertingPattern		AlertingPattern OPTIONAL,
    msisdn			[0] ISDN-AddressString OPTIONAL
}

USSD-Res ::= SEQUENCE {
    ussd-DataCodingScheme	USSD-DataCodingScheme,
    ussd-String			USSD-String,
    ...
}
USSD-DataCodingScheme ::= OCTET STRING (SIZE (1))
-- The structure of the USSD-DataCodingScheme is defined by
-- the Cell Broadcast Data Coding Scheme as described in
-- TS 3GPP TS 23.038 [25]
USSD-String ::= OCTET STRING (SIZE (1..maxUSSD-StringLength))
-- The structure of the contents of the USSD-String is dependent
-- on the USSD-DataCodingScheme as described in TS 3GPP TS 23.038 [25].
maxUSSD-StringLength INTEGER ::= 160

Password ::= NumericString (FROM ("0"|"1"|"2"|"3"|"4"|"5"|"6"|"7"|"8"|"9")) (SIZE (4))

SS-List ::= SEQUENCE SIZE (1..maxNumOfSS) OF SS-Code
maxNumOfSS  INTEGER ::= 30

END -- 17.7.4 MAP-SS-DataTypes (Supplementary service data types)
