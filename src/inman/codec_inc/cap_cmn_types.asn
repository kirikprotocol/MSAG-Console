/* $Id$ */
/* ************************************************************************** *
 * Module: CAP Common Data types.                                             *
 * -- 3GPP TS 29.078 V6.4.0 (2004-12)					      *
 * ************************************************************************** *
 * Author: R.V. Gerasimov                                                     *
 * ************************************************************************** */
/* this is reduced version of original module containing only types required  *
 * for INManager.                                                             *
 * - The parametrization by PARAMETERS-BOUND is expanded.                     *
 * - LocationInformationGPRS is renamed to LocationInformationGPRScap in      *
 *   order to avoid conflict with former one from MAP                         *
 * ************************************************************************** */

-- 5	Common CAP Types
-- 5.1	Data types
CAP-datatypes {
    itu-t(0) identified-organization(4) etsi(0) mobileDomain(0)
    umts-network(1) modules(3) cap-datatypes(52) version5(4)} 
DEFINITIONS IMPLICIT TAGS ::= BEGIN
EXPORTS
    AppendFreeFormatData
    ,CalledPartyBCDNumber
    ,CAMEL-FCISMSBillingChargingCharacteristics
    ,EventSpecificInformationSMS
    ,EventTypeSMS
    ,Extensions
--    ,InvokeID
    ,FCISMSBillingChargingCharacteristics
    ,LocationInformationGPRScap
    ,MonitorMode
    ,MO-SMSCause
    ,MT-SMSCause
    ,RPCause
    ,SMS-AddressString
    ,SMSEvent
    ,TimeAndTimezone
    ,TimerID
    ,TimerValue
    ,TPDataCodingScheme
    ,TPProtocolIdentifier
    ,TPShortMessageSpecificInfo
    ,TPValidityPeriod
    ,UnavailableNetworkResource
;

IMPORTS
    Integer4
FROM CS1-DataTypes {itu-t(0) identified-organization(4) etsi(0) inDomain(1)
      in-network(1) modules(0) cs1-datatypes(2) version1(0)}
    CriticalityType

FROM IN-CS2-datatypes {itu-t(0) identified-organization(4) etsi(0) inDomain(1)
      in-network(1) cs2(20) modules(0) in-cs2-datatypes(0) version1(0)}

    AddressString,
    ISDN-AddressString
FROM MAP-CommonDataTypes {itu-t(0) identified-organization(4) etsi(0)
      mobileDomain(0) gsm-Network(1) modules(3) map-CommonDataTypes(18)
      version10(10)}

    GeographicalInformation,
    LSAIdentity,
    RAIdentity
FROM MAP-MS-DataTypes {itu-t(0) identified-organization(4) etsi(0)
    mobileDomain(0) gsm-Network(1) modules(3) map-MS-DataTypes(11) version10(10)}

    ExtensionContainer
FROM MAP-ExtensionDataTypes {itu-t(0) identified-organization(4) etsi(0)
    mobileDomain(0) gsm-Network(1) modules(3) map-ExtensionDataTypes(21) version10(10)}

    Code
FROM Remote-Operations-Information-Objects
    { joint-iso-itu-t remote-operations(4) informationObjects(5) version1(0) }
    
/*  EXTENSION, SupportedExtensions
FROM CAP-classes { itu-t(0) identified-organization(4) etsi(0) mobileDomain(0)
      umts-network(1) modules(3) cap-classes(54) version4(3) } 
*/
;


AppendFreeFormatData ::= ENUMERATED { overwrite (0), append (1) }

CalledPartyBCDNumber ::= OCTET STRING (SIZE (capMinCalledPartyBCDNumberLength ..
						capMaxCalledPartyBCDNumberLength))
-- Indicates the Called Party Number, including service selection information.
-- Refer to 3GPP TS 24.008 [9] for encoding.
-- This data type carries only the 'type of number', 'numbering plan
-- identification' and 'number digit' fields defined in 3GPP TS 24.008 [9];
-- it does not carry the 'called party BCD number IEI' or 'length of called
-- party BCD number contents'.
-- In the context of the DestinationSubscriberNumber field in ConnectSMSArg or 
-- InitialDPSMSArg, a CalledPartyBCDNumber may also contain an alphanumeric 
-- character string. In this case, type-of-number '101'B is used, in accordance 
-- with 3GPP TS 23.040 [6]. The address is coded in accordance with the 
-- GSM 7-bit default alphabet definition and the SMS packing rules 
-- as specified in 3GPP TS 23.038 [15] in this case.
capMinCalledPartyBCDNumberLength INTEGER ::= 1
capMaxCalledPartyBCDNumberLength INTEGER ::= 41

CAMEL-FCISMSBillingChargingCharacteristics ::= CHOICE {
    fCIBCCCAMELsequence1	[0] SEQUENCE {
	freeFormatData			[0] OCTET STRING (SIZE
					    (capMinFCIBillingChargingDataLength ..
						capMaxFCIBillingChargingDataLength)),
	appendFreeFormatData		[1] AppendFreeFormatData DEFAULT overwrite
    }
}
capMinFCIBillingChargingDataLength INTEGER ::= 1
capMaxFCIBillingChargingDataLength INTEGER ::= 160


EventSpecificInformationSMS ::= CHOICE {
    o-smsFailureSpecificInfo	[0]	SEQUENCE {
	failureCause  [0]  MO-SMSCause OPTIONAL,
	...
    },
    o-smsSubmissionSpecificInfo	[1]	SEQUENCE {
    -- no specific info defined -- ...
    },
    t-smsFailureSpecificInfo	[2]	SEQUENCE {
	failureCause  [0]  MT-SMSCause OPTIONAL,
	...
    },
    t-smsDeliverySpecificInfo	[3]	SEQUENCE {
	-- no specific info defined -- ...
    }
}

EventTypeSMS ::= ENUMERATED {
    sms-CollectedInfo(1), o-smsFailure(2), o-smsSubmission(3),
    sms-DeliveryRequested(11), t-smsFailure(12), t-smsDelivery(13)
}
-- Values sms-CollectedInfo and sms-DeliveryRequested may be used for TDPs only.

Extensions ::= SEQUENCE SIZE (1..capNumOfExtensions) OF ExtensionField
-- This parameter indicates an extension of an argument data type.
-- Its content is network operator specific
capNumOfExtensions INTEGER ::= 10

ExtensionField ::= SEQUENCE {
/* GVR: original definition was:
  type         EXTENSION.&id({SupportedExtensions}),
  -- shall identify the value of an EXTENSION type
  criticality  CriticalityType DEFAULT ignore,
  value        [1]  EXTENSION.&ExtensionType({SupportedExtensions}{@type}),
  ...
*/
  type         Code,
  -- shall identify the value of an EXTENSION type
  criticality  CriticalityType DEFAULT ignore,
  -- GVR:  implicit tagging is in use, so just use the OCTET STRING  instead of OpenType
  value        [1]  ANY /*DEFINED BY type*/,
  ...
}

-- InvokeID ::= INTEGER(-128..127)

FCISMSBillingChargingCharacteristics ::= 
    OCTET STRING (SIZE (capMinFCIBillingChargingLength .. capMaxFCIBillingChargingLength))
	(CONSTRAINED BY {-- shall be the result of the BER-encoded value of type -
	    CAMEL-FCISMSBillingChargingCharacteristics})
-- This parameter indicates the SMS billing and/or charging characteristics.
-- The violation of the UserDefinedConstraint shall be handled as an ASN.1 syntax error.
capMinFCIBillingChargingLength INTEGER ::= 5
capMaxFCIBillingChargingLength INTEGER ::= 225

LocationInformationGPRScap ::= SEQUENCE {
    cellGlobalIdOrServiceAreaIdOrLAI	[0] OCTET STRING (SIZE(5..7))	OPTIONAL,
    routeingAreaIdentity		[1] RAIdentity			OPTIONAL,
    geographicalInformation		[2] GeographicalInformation	OPTIONAL,
    sgsn-Number				[3] ISDN-AddressString		OPTIONAL,
    selectedLSAIdentity			[4] LSAIdentity			OPTIONAL,
    extensionContainer			[5] ExtensionContainer		OPTIONAL,
    ...,
    sai-Present				[6] NULL			OPTIONAL
}
-- cellGlobalIdOrServiceAreaIdOrLAI shall contain the value part of the
-- CellGlobalIdOrServiceAreaIdFixedLength type or the LAIFixedLength type (i.e. excluding tags
-- and lengths) as defined in 3GPP TS 29.002 [13].
-- sai-Present indicates that the cellGlobalIdOrServiceAreaIdOrLAI parameter contains
-- a Service Area Identity.

MonitorMode ::= ENUMERATED {
    interrupted(0), notifyAndContinue(1), transparent(2)}
-- Indicates the event is relayed and/or processed by the SSP.
-- Transparent means that the gsmSSF or gprsSSF does not notify the gsmSCF of the event.
-- For the use of this parameter refer to the procedure descriptions in clause 11.
-- For the RequestNotificationCharging operation, 'interrupted' shall not be used in MonitorMode.

MO-SMSCause ::= ENUMERATED {
    systemFailure(0), unexpectedDataValue(1), facilityNotSupported(2),
    sM-DeliveryFailure(3), releaseFromRadioInterface(4)}
-- MO SMS error values which are reported to gsmSCF.
-- Most of these values are received from the SMSC as a response to
-- MO-ForwardSM operation.

MT-SMSCause ::= OCTET STRING(SIZE (1))
-- This variable is sent to the gsmSCF for a Short Message delivery failure
-- notification.
-- If the delivery failure is due to RP-ERROR RPDU received from the MS,
-- then MT-SMSCause shall be set to the RP-Cause component in the RP-ERROR RPDU.
-- Refer to 3G TS 24.011 [10] for the encoding of RP-Cause values.
-- Otherwise, if the delivery failure is due to internal failure in the MSC or SGSN
-- or time-out from the MS, then MT-SMSCause shall be set to 'Protocol error,
-- unspecified', as defined in 3G TS 24.011 [10].

RPCause ::= OCTET STRING (SIZE (1))
-- RP cause according to 3GPP TS 24.011 [10] or 3GPP TS 29.002 [11].
-- GsmSCF shall send this cause in the ReleaseSMS operation.
-- For a MO-SMS service, the MSC or SGSN shall send the RP Cause to the originating MS.
-- It shall be used to overwrite the RP-Cause element in the RP-ERROR RPDU.
-- For a MT-SMS service, the MSC or SGSN shall send the RP Cause to the sending SMS-GMSC.
-- It shall be used to overwrite the RP-Cause element in the RP-ERROR RPDU.

SMS-AddressString ::= AddressString(SIZE (1..maxSMS-AddressStringLength))
-- An SMS-AddressString may contain an alphanumeric character string. In this 
-- case, a nature of address indicator '101'B is used, in accordance with 
-- 3GPP TS 23.040 [6]. The address is coded in accordance with the GSM 7-bit 
-- default alphabet definition and the SMS packing rules as specified in 
-- 3GPP TS 23.038 [15] in this case.
maxSMS-AddressStringLength INTEGER ::= 11

SMSEvent ::= SEQUENCE {
    eventTypeSMS	[0]	EventTypeSMS,
    monitorMode		[1]	MonitorMode
}

TimeAndTimezone ::= OCTET STRING (SIZE (capMinTimeAndTimezoneLength .. 
					capMaxTimeAndTimezoneLength))
--  Indicates the time and timezone, relative to GMT. This parameter is BCD encoded.
--  The year digit indicating millenium occupies bits 0-3 of the first octet, and the year
--  digit indicating century occupies bits 4-7 of the first octet.
--  The year digit indicating decade occupies bits 0-3 of the second octet, whilst the digit
--  indicating the year within the decade occupies bits 4-7 of the second octet.
--  The most significant month digit occupies bits 0-3 of the third octet, and the least
--  significant month digit occupies bits 4-7 of the third octet.
--  The most significant day digit occupies bits 0-3 of the fourth octet, and the least
--  significant day digit occupies bits 4-7 of the fourth octet.
--  The most significant hours digit occupies bits 0-3 of the fifth octet, and the least
--  significant hours digit occupies bits 4-7 of the fifth octet.
--  The most significant minutes digit occupies bits 0-3 of the sixth octet, and the least
--  significant minutes digit occupies bits 4-7 of the sixth octet.
--  The most significant seconds digit occupies bits 0-3 of the seventh octet, and the least
--  significant seconds digit occupies bits 4-7 of the seventh octet.
--
--  The timezone information occupies the eighth octet. For the encoding of Timezone refer to
--  3GPP TS 23.040 [6].
--
--  The BCD digits are packed and encoded as follows:
--
--  Bit	 7  6  5   4  |  3  2  1  0
--       2nd digit    | 1st digit          Octet 1
--       3rd digit    | 4th digit          Octet 2
--           	         ..                   ..
--       nth digit    | n-1th digit        Octet m
--
--       0000		digit 0
--       0001		digit 1
--       0010		digit 2
--       0011		digit 3
--       0100		digit 4
--       0101		digit 5
--       0110		digit 6
--       0111		digit 7
--       1000		digit 8
--       1001		digit 9
--       1010		spare
--       1011		spare
--       1100		spare
--       1101		spare
--       1110		spare
--       1101		spare
--
-- where the leftmost bit of the digit is either bit 7 or bit 3 of the octet.
capMinTimeAndTimezoneLength INTEGER ::= 8
capMaxTimeAndTimezoneLength INTEGER ::= 8

TimerID ::= ENUMERATED { tssf (0) }
-- Indicates the timer to be reset.

TimerValue ::= Integer4
-- Indicates the timer value (in seconds).

TPDataCodingScheme ::= OCTET STRING(SIZE (1))
-- TP Data Coding Scheme according to 3GPP TS 23.040 [6]

TPProtocolIdentifier ::= OCTET STRING(SIZE (1))
-- indicates the protocol used above the SM-Transfer Layer as specified in 3GPP TS 23.040 [6].

TPShortMessageSpecificInfo ::= OCTET STRING(SIZE (1))
-- contains the 1st octect of the applicable TPDU or the SMS-COMMAND TPDU as specified in
-- 3GPP TS 23.040 [6].

TPValidityPeriod ::= OCTET STRING(SIZE (1..7))
-- indicates the length of the validity period or the absolute time of the validity
-- period termination as specified in 3GPP TS 23.040 [6].
-- the length of ValidityPeriod is either 1 octet or 7 octets

UnavailableNetworkResource ::= ENUMERATED {
    unavailableResources(0), componentFailure(1),
    basicCallProcessingException(2), resourceStatusFailure(3), endUserFailure(4)
}
-- Indicates the network resource that failed.

END -- 5.1 CAP-datatypes
