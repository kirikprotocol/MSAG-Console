/* $Id$ */
/* ************************************************************************** *
 * Module: IN CS2 data types.                                                 *
 * ************************************************************************** *
 * Author: R.V. Gerasimov                                                     *
 * ************************************************************************** */
IN-CS2-datatypes {
    itu-t(0) identified-organization(4) etsi(0) inDomain(1)
    in-network(1) cs2(20) modules(0) in-cs2-datatypes (0) version1(0)}
DEFINITIONS IMPLICIT TAGS ::=
-- this is reduced version of original module containing only types required for IN-Manager
BEGIN

CriticalityType	::= ENUMERATED { ignore (0), abort (1) } 

MiscCallInfo	::= SEQUENCE {
    messageType	[0]	ENUMERATED { request (0), notification (1), ... }
}

END -- IN-CS2-datatypes
