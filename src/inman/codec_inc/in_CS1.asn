/* $Id$ */
/* ************************************************************************** *
 * Module: IN CS1 data types.                                                 *
 * ************************************************************************** *
 * Author: R.V. Gerasimov                                                     *
 * ************************************************************************** */
CS1-DataTypes {
    itu-t(0) identified-organization(4) etsi(0) inDomain(1)
    in-network(1) modules(0) cs1-datatypes(2) version1(0)}
-- This module contains the type definitions for the IN CS1 data types.
DEFINITIONS IMPLICIT TAGS ::=
-- this is reduced version of original module containing only types required for IN-Manager
BEGIN

ServiceKey ::= Integer4
-- Information that allows the SCF to choose the appropriate service logic.

Integer4 ::= INTEGER(0..2147483647)

END -- CS1-DataTypes
