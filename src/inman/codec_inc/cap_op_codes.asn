/* $Id$ */
/* ************************************************************************** *
 * Module: CAP Operation codes.                                               *
 * -- 3GPP TS 29.078 V6.4.0 (2004-12)                                         *
 * ************************************************************************** *
 * Author: R.V. Gerasimov                                                     *
 * ************************************************************************** */
-- 5.3	Operation codes
CAP-operationcodes {
    itu-t(0) identified-organization(4) etsi(0) mobileDomain(0) umts-network(1)
    modules(3) cap-operationcodes(53) version5(4)}
DEFINITIONS ::= BEGIN
IMPORTS
    Code
FROM Remote-Operations-Information-Objects {
    joint-iso-itu-t remote-operations(4) informationObjects(5) version1(0) }
;

-- the operations are grouped by the identified operation packages.

-- gsmSCF activation Package
opcode-initialDP				Code ::= local: 0
-- gsmSCF/gsmSRF activation of assist Package
opcode-assistRequestInstructions		Code ::= local: 16
-- Assist connection establishment Package
opcode-establishTemporaryConnection		Code ::= local: 17
-- Generic disconnect resource Package
opcode-disconnectForwardConnection		Code ::= local: 18
opcode-dFCWithArgument				Code ::= local: 86
-- Non-assisted connection establishment Package

opcode-connectToResource			Code ::= local: 19
-- Connect Package (elementary gsmSSF function)
opcode-connect					Code ::= local: 20
-- Call handling Package (elementary gsmSSF function)
opcode-releaseCall				Code ::= local: 22
-- BCSM Event handling Package
opcode-requestReportBCSMEvent			Code ::= local: 23
opcode-eventReportBCSM				Code ::= local: 24
-- gsmSSF call processing Package
opcode-continue					Code ::= local: 31
-- gsmSCF call initiation Package
opcode-initiateCallAttempt			Code ::= local: 32
-- Timer Package
opcode-resetTimer				Code ::= local: 33
-- Billing Package
opcode-furnishChargingInformation		Code ::= local: 34
-- Charging Package
opcode-applyCharging				Code ::= local: 35
opcode-applyChargingReport			Code ::= local: 36
-- Traffic management Package
opcode-callGap					Code ::= local: 41
-- Call report Package
opcode-callInformationReport			Code ::= local: 44
opcode-callInformationRequest			Code ::= local: 45
-- Signalling control Package
opcode-sendChargingInformation			Code ::= local: 46
-- Specialized resource control Package
opcode-playAnnouncement				Code ::= local: 47
opcode-promptAndCollectUserInformation		Code ::= local: 48
opcode-specializedResourceReport		Code ::= local: 49
-- Cancel Package
opcode-cancel					Code ::= local: 53
-- Activity Test Package
opcode-activityTest				Code ::= local: 55
-- CPH Response Package
opcode-continueWithArgument			Code ::= local: 88
opcode-disconnectLeg				Code ::= local: 90
opcode-moveLeg					Code ::= local: 93
opcode-splitLeg					Code ::= local: 95
-- Exception Inform Package
opcode-entityReleased				Code ::= local: 96
-- Play Tone Package
opcode-playTone					Code ::= local: 97

-- Sms Activation Package
opcode-initialDPSMS				Code ::= local: 60
-- Sms Billing Package
opcode-furnishChargingInformationSMS		Code ::= local: 61
-- Sms Connect Package
opcode-connectSMS				Code ::= local: 62
-- Sms Event Handling Package
opcode-requestReportSMSEvent			Code ::= local: 63
opcode-eventReportSMS				Code ::= local: 64
-- Sms Processing Package
opcode-continueSMS				Code ::= local: 65
-- Sms Release Package	
opcode-releaseSMS				Code ::= local: 66
-- Sms Timer Package
opcode-resetTimerSMS				Code ::= local: 67

-- Gprs Activity Test Package
opcode-activityTestGPRS				Code ::= local: 70
-- Gprs Charging Package
opcode-applyChargingGPRS			Code ::= local: 71
opcode-applyChargingReportGPRS			Code ::= local: 72
-- Gprs Cancel Package
opcode-cancelGPRS				Code ::= local: 73
-- Gprs Connect Package
opcode-connectGPRS				Code ::= local: 74
-- Gprs Processing Package
opcode-continueGPRS				Code ::= local: 75
-- Gprs Exception Information Package
opcode-entityReleasedGPRS			Code ::= local: 76
-- Gprs Billing Package
opcode-furnishChargingInformationGPRS		Code ::= local: 77
-- Gprs Scf Activation Package
opcode-initialDPGPRS				Code ::= local: 78
-- Gprs Release Package
opcode-releaseGPRS				Code ::= local: 79
-- Gprs Event Handling Package
opcode-eventReportGPRS				Code ::= local: 80
opcode-requestReportGPRSEvent			Code ::= local: 81
-- Gprs Timer Package
opcode-resetTimerGPRS				Code ::= local: 82
-- Gprs Charge Advice Package
opcode-sendChargingInformationGPRS		Code ::= local: 83

END -- 5.3 Operation codes
