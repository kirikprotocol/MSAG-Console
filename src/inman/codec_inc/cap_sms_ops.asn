/* $Id$ */
/* ************************************************************************** *
 * Module: CAP SMS operations and arguments.                                  *
 * -- 3GPP TS 29.078 V6.4.0 (2004-12)					      *
 * ************************************************************************** *
 * Author: R.V. Gerasimov                                                     *
 * ************************************************************************** */
/* The parametrization by PARAMETERS-BOUND is expanded.                       *
 * ************************************************************************** */

-- 7	SMS Control
-- 7.1	SMS operations and arguments
CAP-SMS-ops-args {
    itu-t(0) identified-organization(4) etsi(0) mobileDomain(0) umts-network(1)
    modules(3) cap-SMS-ops-args(105) version5(4)}
-- The module CAP-SMS-ops-args is updated to version5(4) for Rel-6. The OPERATION definitions
-- are not modified.
DEFINITIONS IMPLICIT TAGS::= BEGIN
-- This module contains the operations and operation arguments used for the
-- smsSSF- gsmSCF interface, for the control of MO-SMS and MT-SMS.

-- The table in subclause 2.1 lists the specifications that contain the modules
-- that are used by CAP.
IMPORTS
    OPERATION,
    ERROR
FROM Remote-Operations-Information-Objects {
    joint-iso-itu-t remote-operations(4) informationObjects(5) version1(0) }

    ServiceKey
FROM CS1-DataTypes {itu-t(0) identified-organization(4) etsi(0) inDomain(1) in-network(1)
    modules(0) cs1-datatypes(2) version1(0)}

    MiscCallInfo
FROM CS2-datatypes {itu-t(0) identified-organization(4) etsi(0) inDomain(1) in-network(1)
    cs2(20) modules(0) in-cs2-datatypes (0) version1(0)}

    IMEI,
    IMSI,
    ISDN-AddressString
FROM MAP-CommonDataTypes {itu-t(0) identified-organization(4) etsi(0) mobileDomain(0)
    gsm-Network(1) modules(3) map-CommonDataTypes(18) version10(10)}

    GPRSMSClass,
    LocationInformation,
    MS-Classmark2
FROM MAP-MS-DataTypes {itu-t(0) identified-organization(4) etsi(0) mobileDomain(0)
    gsm-Network(1) modules(3) map-MS-DataTypes(11) version10(10)}

    opcode-connectSMS,
    opcode-continueSMS,
    opcode-eventReportSMS,
    opcode-furnishChargingInformationSMS,
    opcode-initialDPSMS,
    opcode-releaseSMS,
    opcode-requestReportSMSEvent,
    opcode-resetTimerSMS
FROM CAP-operationcodes {
    itu-t(0) identified-organization(4) etsi(0) mobileDomain(0) umts-network(1)
    modules(3) cap-operationcodes(53) version5(4) }
-- The CAP Operation identifiers for CAP V3 and CAP V4 for SMS in Rel-6 are the same as in Rel-5.

    CalledPartyBCDNumber,
    EventSpecificInformationSMS,
    EventTypeSMS,
    Extensions,
    FCISMSBillingChargingCharacteristics,
    LocationInformationGPRScap,
    RPCause,
    SMS-AddressString,
    SMSEvent,
    TimeAndTimezone,
    TimerID,
    TimerValue,
    TPDataCodingScheme,
    TPProtocolIdentifier,
    TPShortMessageSpecificInfo,
    TPValidityPeriod
FROM CAP-datatypes {
    itu-t(0) identified-organization(4) etsi(0) mobileDomain(0)
    umts-network(1) modules(3) cap-datatypes(52) version5(4) }
-- For Rel-6, the CAP-datatypes module is updated to version5(4); Object Identifier 'datatypes'
-- is also updated to version5(4). As a result, the present module uses Rel-6 data type definitions.

    missingCustomerRecord,
    missingParameter,
    parameterOutOfRange,
    systemFailure,
    taskRefused,
    unexpectedComponentSequence,
    unexpectedDataValue,
    unexpectedParameter
FROM CAP-errortypes {
    itu-t(0) identified-organization(4) etsi(0) mobileDomain(0) umts-network(1)
    modules(3) cap-errortypes(51) version5(4) }
-- For Rel-6, the CAP-errortypes module is updated to version5(4); Object Identifier
-- 'errortypes' is also updated to version5(4). As a result, the present module uses Rel-6
-- error type definitions.

    CallReferenceNumber
FROM MAP-CH-DataTypes {itu-t(0) identified-organization(4) etsi(0) mobileDomain(0)
    gsm-Network(1) modules(3) map-CH-DataTypes(13) version10(10)}
;

-- Basic errors for SMS operations
CAP-SMSErrors ERROR ::= {
    missingParameter | taskRefused | unexpectedComponentSequence |
    unexpectedDataValue | unexpectedParameter
}
-- Errors for RequestReportSMSEvent operation
CAP-SMSEventErrors ERROR ::= {
	parameterOutOfRange | systemFailure | CAP-SMSErrors
}

-- Errors for InitialDPSMS operation
CAP-IniDPSMSErrors ERROR ::= {
	missingCustomerRecord | CAP-SMSEventErrors
}

-- Errors for ResetTimerSMS operation
CAP-SMSTimerErrors ERROR ::= {
    parameterOutOfRange | CAP-SMSErrors
}


connectSMS OPERATION ::= {
    ARGUMENT		ConnectSMSArg
    RETURN RESULT	FALSE
    ERRORS		{ CAP-SMSEventErrors }
    CODE		opcode-connectSMS
}
--  Direction: gsmSCF -> gsmSSF or gprsSSF, Timer: Tconsms
--  This operation is used to request the smsSSF to perform the SMS processing
--  actions to route or forward a short message to a specified destination.

ConnectSMSArg ::= SEQUENCE {
    callingPartysNumber		[0] SMS-AddressString		OPTIONAL,
    destinationSubscriberNumber	[1] CalledPartyBCDNumber	OPTIONAL,
    sMSCAddress			[2] ISDN-AddressString		OPTIONAL,
    extensions			[10] Extensions			OPTIONAL,
    ...
}

continueSMS OPERATION ::= {
    RETURN RESULT	FALSE
    ALWAYS RESPONDS	FALSE
    CODE		opcode-continueSMS
}
-- Direction: gsmSCF -> smsSSF, Timer: Tcuesms 
-- This operation is used to request the smsSSF to proceed with
-- Short Message processing at the DP at which it previously suspended
-- Short Message processing to await gsmSCF instructions (i.e. proceed
-- to the next Point in Association in the SMS FSM). The smsSSF
-- continues SMS processing without substituting new data from the gsmSCF.

eventReportSMS OPERATION ::= {
    ARGUMENT		EventReportSMSArg
    RETURN RESULT	FALSE
    ALWAYS RESPONDS	FALSE
    CODE		opcode-eventReportSMS
}
--  Direction: gsmSSF or gprsSSF -> gsmSCF, Timer: Terbsms
--  This operation is used to notify the gsmSCF of a Short Message related event (FSM events
--  such as submission, delivery or failure) previously requested by the gsmSCF in a
--  RequestReportSMSEvent operation.

EventReportSMSArg ::= SEQUENCE {
    eventTypeSMS		[0] EventTypeSMS,
    eventSpecificInformationSMS	[1] EventSpecificInformationSMS		OPTIONAL,
    miscCallInfo		[2] MiscCallInfo DEFAULT {messageType request},
    extensions			[10] Extensions				OPTIONAL,
    ...
}

furnishChargingInformationSMS OPERATION ::= {
    ARGUMENT		FurnishChargingInformationSMSArg
    RETURN RESULT	FALSE
    ERRORS		{ CAP-SMSErrors }
    CODE		opcode-furnishChargingInformationSMS
}
--  Direction: gsmSCF ?? gsmSSF or gprsSSF, Timer: Tfcisms 
--  This operation is used to request the smsSSF to generate, register a charging record
--  or to include some information in the default SM record. The registered charging record is
--  intended for off line charging of the Short Message.

FurnishChargingInformationSMSArg ::= FCISMSBillingChargingCharacteristics

initialDPSMS OPERATION ::= {
    ARGUMENT		InitialDPSMSArg
    RETURN RESULT	FALSE
    ERRORS		{ CAP-IniDPSMSErrors }
    CODE		opcode-initialDPSMS
}
--  Direction: gsmSSF or gprsSSF -> gsmSCF, Timer: Tidpsms
--  This operation is used after a TDP to indicate request for service.

InitialDPSMSArg ::= SEQUENCE {
    serviceKey			[0] ServiceKey,
    destinationSubscriberNumber	[1] CalledPartyBCDNumber	OPTIONAL,
    callingPartyNumber		[2] SMS-AddressString		OPTIONAL,
    eventTypeSMS		[3] EventTypeSMS		OPTIONAL,
    iMSI			[4] IMSI			OPTIONAL,
    locationInformationMSC	[5] LocationInformation		OPTIONAL,
    locationInformationGPRS	[6] LocationInformationGPRScap	OPTIONAL,
    sMSCAddress			[7] ISDN-AddressString		OPTIONAL,
    timeAndTimezone		[8] TimeAndTimezone		OPTIONAL,
    tPShortMessageSpecificInfo	[9] TPShortMessageSpecificInfo	OPTIONAL,
    tPProtocolIdentifier	[10] TPProtocolIdentifier	OPTIONAL,
    tPDataCodingScheme		[11] TPDataCodingScheme		OPTIONAL,
    tPValidityPeriod		[12] TPValidityPeriod		OPTIONAL,
    extensions			[13] Extensions			OPTIONAL,
    ...,
    smsReferenceNumber		[14] CallReferenceNumber	OPTIONAL,
    mscAddress			[15] ISDN-AddressString		OPTIONAL,
    sgsn-Number			[16] ISDN-AddressString		OPTIONAL,
    ms-Classmark2		[17] MS-Classmark2		OPTIONAL,
    gPRSMSClass 		[18] GPRSMSClass		OPTIONAL,
    iMEI			[19] IMEI			OPTIONAL,
    calledPartyNumber		[20] ISDN-AddressString		OPTIONAL
}

releaseSMS OPERATION ::= {
    ARGUMENT		ReleaseSMSArg
    RETURN RESULT	FALSE
    ALWAYS RESPONDS	FALSE
    CODE		opcode-releaseSMS
}
--  Direction: gsmSCF -> gsmSSF or gprsSSF, Timer: Trelsms
--  This operation is used to prevent an attempt to submit or deliver a short message. 

ReleaseSMSArg ::= RPCause

requestReportSMSEvent OPERATION ::= {
    ARGUMENT		RequestReportSMSEventArg
    RETURN RESULT	FALSE
    ERRORS		{ CAP-SMSEventErrors }
    CODE		opcode-requestReportSMSEvent
}
--  Direction: gsmSCF -> gsmSSF or gprsSSF, Timer: Trrbsms
--  This operation is used to request the gsmSSF or gprsSSF to monitor for a
--  Short Message related event (FSM events such as submission, delivery or failure)
--  and to send a notification to the gsmSCF when the event is detected.

RequestReportSMSEventArg ::= SEQUENCE {
    sMSEvents		[0] SEQUENCE SIZE (1..capNumOfSMSEvents) OF SMSEvent,
    extensions		[10] Extensions		OPTIONAL,
    ...
}
--  Indicates the Short Message related events(s) for notification.
capNumOfSMSEvents INTEGER ::= 10

resetTimerSMS OPERATION ::= {
    ARGUMENT		ResetTimerSMSArg
    RETURN RESULT	FALSE
    ERRORS		{ CAP-SMSTimerErrors }
    CODE		opcode-resetTimerSMS
}
-- Direction: gsmSCF -> smsSSF, Timer: Trtsms 
-- This operation is used to request the smsSSF to refresh an application
-- timer in the smsSSF.

ResetTimerSMSArg ::= SEQUENCE {
    timerID		[0] TimerID	DEFAULT tssf,
    timervalue		[1] TimerValue,
    extensions		[2] Extensions	OPTIONAL,
    ...
}

END -- 7.1 SMS operations and arguments
