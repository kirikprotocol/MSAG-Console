/* $Id$ */
/* ************************************************************************** *
 * Module: CAP Error types.                                                   *
 * -- 3GPP TS 29.078 V6.4.0 (2004-12)                                         *
 * ************************************************************************** *
 * Author: R.V. Gerasimov                                                     *
 * ************************************************************************** */
/* this is reduced version of original module containing only types           *
 * required for INManager.                                                    *
 * ************************************************************************** */

-- 5.2	Error types
CAP-errortypes {
    itu-t(0) identified-organization(4) etsi(0) mobileDomain(0) umts-network(1)
    modules(3) cap-errortypes(51) version5(4)}
-- This module contains the type definitions for the CAP Error Types.
DEFINITIONS IMPLICIT TAGS ::= BEGIN
IMPORTS
    ERROR
FROM Remote-Operations-Information-Objects {
    joint-iso-itu-t remote-operations(4) informationObjects(5) version1(0) }

    UnavailableNetworkResource
FROM CAP-datatypes {
    itu-t(0) identified-organization(4) etsi(0) mobileDomain(0)
    umts-network(1) modules(3) cap-datatypes(52) version5(4) } 

    errcode-missingCustomerRecord,
    errcode-missingParameter,
    errcode-parameterOutOfRange,
    errcode-systemFailure,
    errcode-taskRefused,
    errcode-unexpectedComponentSequence,
    errcode-unexpectedDataValue,
    errcode-unexpectedParameter
FROM CAP-errorcodes {
    itu-t(0) identified-organization(4) etsi(0) mobileDomain(0) umts-network(1)
    modules(3) cap-errorcodes(57) version5(4) }
;

-- TYPE DEFINITION FOR CAP ERROR TYPES FOLLOWS

-- The operation has been canceled.
-- The operation failed to be canceled.
-- The establish temporary connection failed.
-- The caller response was not as expected.

missingCustomerRecord ERROR ::= { CODE	errcode-missingCustomerRecord }
-- The Service Logic Program could not be found in the gsmSCF.

missingParameter ERROR ::= { CODE	errcode-missingParameter }
-- An expected optional parameter was not received.

parameterOutOfRange ERROR ::= { CODE	errcode-parameterOutOfRange }
-- The parameter was not as expected (e.g. missing or out of range).

-- The requested information cannot be found.

systemFailure ERROR ::= {
    PARAMETER	UnavailableNetworkResource
    CODE	errcode-systemFailure
}
-- The operation could not be completed due to a system failure at the serving physical entity.

taskRefused ERROR ::= {
    PARAMETER	ENUMERATED { generic(0), unobtainable(1), congestion(2) }
    CODE	errcode-taskRefused
}
-- An entity normally capable of the task requested cannot or chooses not to perform the task at
-- this time. This includes error situations like congestion and unobtainable address as used in
-- e.g. the connect operation.)

-- A requested resource is not available at the serving entity.

unexpectedComponentSequence ERROR ::= { CODE	errcode-unexpectedComponentSequence }
-- An incorrect sequence of Components was received (e.g. 'DisconnectForwardConnection'
-- followed by 'PlayAnnouncement').

unexpectedDataValue ERROR ::= { CODE	errcode-unexpectedDataValue }
-- The data value was not as expected (e.g. route number expected but billing number received)

unexpectedParameter ERROR ::= { CODE	errcode-unexpectedParameter }
-- A parameter received was not expected.

-- Leg not known to the gsmSSF.
-- Call Segment not known to the gsmSSF.
-- PDPID not known by the receiving entity.

END -- 5.2 Error types
