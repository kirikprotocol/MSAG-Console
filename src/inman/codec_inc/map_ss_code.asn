/* $Id$ */
/* ************************************************************************** *
 * Module: MAP Supplementary service codes.                                   *
 * -- 3GPP TS 29.002 V7.2.0 (2005-12)					      *
 * ************************************************************************** *
 * Author: R.V. Gerasimov                                                     *
 * ************************************************************************** */

-- 17.7.5	Supplementary service codes
MAP-SS-Code {
   itu-t(0) identified-organization (4) etsi (0) mobileDomain (0)
   gsm-Network (1) modules (3) map-SS-Code (15) version10 (10)}
DEFINITIONS ::= BEGIN

SS-Code ::= OCTET STRING (SIZE (1))
-- This type is used to represent the code identifying a single
-- supplementary service, a group of supplementary services, or
-- all supplementary services. The services and abbreviations
-- used are defined in TS 3GPP TS 22.004 [5]. The internal structure is
-- defined as follows:
--
-- bits 87654321: group (bits 8765), and specific service
-- (bits 4321)
END -- 17.7.5 MAP-SS-Code (Supplementary service codes)
