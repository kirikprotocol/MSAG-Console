/* $Id$ */
/* ************************************************************************** *
 * Module: CAP Error codes.                                                   *
 * -- 3GPP TS 29.078 V6.4.0 (2004-12)                                         *
 * ************************************************************************** *
 * Author: R.V. Gerasimov                                                     *
 * ************************************************************************** */

-- 5.4 Error codes
CAP-errorcodes {
    itu-t(0) identified-organization(4) etsi(0) mobileDomain(0) umts-network(1)
    modules(3) cap-errorcodes(57) version5(4)}
DEFINITIONS ::= BEGIN
IMPORTS
    Code
FROM Remote-Operations-Information-Objects {
    joint-iso-itu-t remote-operations(4) informationObjects(5) version1(0) }
;

errcode-canceled			Code ::= local: 0
errcode-cancelFailed			Code ::= local: 1
errcode-eTCFailed			Code ::= local: 3
errcode-improperCallerResponse		Code ::= local: 4
errcode-missingCustomerRecord		Code ::= local: 6
errcode-missingParameter		Code ::= local: 7
errcode-parameterOutOfRange		Code ::= local: 8
errcode-requestedInfoError		Code ::= local: 10
errcode-systemFailure			Code ::= local: 11
errcode-taskRefused			Code ::= local: 12
errcode-unavailableResource		Code ::= local: 13
errcode-unexpectedComponentSequence	Code ::= local: 14
errcode-unexpectedDataValue		Code ::= local: 15
errcode-unexpectedParameter		Code ::= local: 16
errcode-unknownLegID			Code ::= local: 17
errcode-unknownPDPID			Code ::= local: 50
errcode-unknownCSID			Code ::= local: 51

END -- 5.4	Error codes
