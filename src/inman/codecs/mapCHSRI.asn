/* $Id$ */
/* ************************************************************************** *
 * This file contains ASN.1 definitions for MAP-SEND-ROUTING-INFO (10.1)      *
 * service operations.							      *
 * ************************************************************************** *
 * Author: R.V. Gerasimov						      *
 * -- 3GPP TS 29.002 V7.2.0 (2005-12)					      *
 * ************************************************************************** */

/* MAP-CH-SRI:

17.3.2.6	Location Information Retrieval

This application-context is used between GMSC and HLR or between GMSC and NPLR
or between gsmSCF and HLR when retrieving location information.
For the GMSC - NPLR interface version 1, version 2 and version 3 of this
application context are applicable.

locationInfoRetrievalContext-v3 APPLICATION-CONTEXT ::= {
    -- Responder is HLR or NPLR if Initiator is GMSC
    -- Responder is HLR if Initiator is gsmSCF
    INITIATOR CONSUMER OF { interrogationPackage-v3 }
    ID			{ map-ac locInfoRetrieval(5) version3(3) } 
}

The following application-context-name is assigned to the v2-equivalent application-context:
    ID	{map-ac locInfoRetrieval(5) version2(2)}

The following application-context-name is assigned to the v1-equivalent application-context:
    ID	{map-ac locInfoRetrieval(5) version1(1)}


17.2.2.10 Interrogation

This operation package includes the operations required for interrogation
procedures between MSC and HLR or NPLR or between HLR and gsmSCF.

interrogationPackage-v3 OPERATION-PACKAGE ::= {
    -- Supplier is HLR or NPLR if Consumer is MSC
    -- Supplier is HLR if Consumer is gsmSCF
    CONSUMER INVOKES { sendRoutingInfo } 
}
The v1-equivalent and v2-equivalent packages can be determined according to
the rules described in clause 17.2.1.
 
 
The APPLICATION-CONTEXT is defined as:

APPLICATION-CONTEXT ::= CLASS {
    &Symmetric		 OPERATION-PACKAGE OPTIONAL,
    &InitiatorConsumerOf OPERATION-PACKAGE OPTIONAL,
    &ResponderConsumerOf OPERATION-PACKAGE OPTIONAL,
    &code		 OBJECT IDENTIFIER
} WITH SYNTAX {
    [ OPERATIONS OF		&Symmetric ]
    [ INITIATOR CONSUMER OF	&InitiatorConsumerOf
      RESPONDER CONSUMER OF	&ResponderConsumerOf ]
    ID &code 
}
* ************************************************************************** */

INMan-mapCHSRI-OIDs
DEFINITIONS ::=
-- GVRoman's NOTE: This module is for informative purposes only. 
-- It denotes OIDs of modules used by map-CH-SRI service.
-- These OIDs are never used in below notation because of 
-- SourceForge's asn1c unable to parse ASN.1 module references
-- with named OID.
BEGIN
-- ******************************************************************* --
-- ROS modules follow
-- ******************************************************************* --
id-ros-InformationObjects OBJECT IDENTIFIER ::= {
    joint-iso-itu-t remote-operations(4) informationObjects(5) version1(0) }

-- ******************************************************************* --
-- MAP modules follow
-- ******************************************************************* --

-- 17.6.6 Errors
id-map-Errors OBJECT IDENTIFIER ::= {
    itu-t(0) identified-organization (4) etsi (0) mobileDomain (0)
    gsm-Network (1) modules (3) map-Errors (10) version10 (10)}

-- 17.7.1 Mobile Service data types
id-map-MS-DataTypes OBJECT IDENTIFIER ::= {
    itu-t(0) identified-organization(4) etsi(0) mobileDomain(0)
    gsm-Network(1) modules(3) map-MS-DataTypes(11) version10(10) }

-- 17.7.4 Supplementary service data types
id-map-SS-DataTypes  OBJECT IDENTIFIER ::= {
    itu-t(0) identified-organization (4) etsi (0) mobileDomain (0)
    gsm-Network (1) modules (3) map-SS-DataTypes (14) version10 (10) }

-- 17.7.5 Supplementary service codes
id-map-SS-Code OBJECT IDENTIFIER ::= {
   itu-t(0) identified-organization (4) etsi (0) mobileDomain (0)
   gsm-Network (1) modules (3) map-SS-Code (15) version10 (10) }

-- 17.7.7 Error data types
id-map-ER-DataTypes OBJECT IDENTIFIER ::= {
   itu-t(0) identified-organization (4) etsi (0) mobileDomain (0)
   gsm-Network (1) modules (3) map-ER-DataTypes (17) version10 (10) }

-- 17.7.8 Common data types
id-map-CommonDataTypes OBJECT IDENTIFIER ::= {
    itu-t(0) identified-organization(4) etsi(0) mobileDomain(0) gsm-Network(1)
    modules(3) map-CommonDataTypes(18) version10(10) }

-- 17.7.11 Extension data types
id-map-Extension-DataTypes OBJECT IDENTIFIER ::= {
    itu-t(0) identified-organization(4) etsi(0) mobileDomain(0) gsm-Network(1)
    modules(3) map-ExtensionDataTypes(21) version10(10) }

id-map-CH-DataTypes OBJECT IDENTIFIER ::= {
    itu-t(0) identified-organization(4) etsi(0) mobileDomain(0)
    gsm-Network(1) modules(3) map-CH-DataTypes(13) version10(10) }

END -- INMan-mapUSS-OIDs

-- ******************************************************************* --
-- MAP modules follow
-- ******************************************************************* --

-- 17.6.3 Call Handling Operations
MAP-CallHandlingOperations-SRI {
   itu-t(0) identified-organization (4) etsi (0) mobileDomain (0)
   gsm-Network (1) modules (3) map-CallHandlingOperations (7) version10 (10)
   sri-version3(53)}
DEFINITIONS ::= BEGIN
-- NOTE: This module is excerpt from MAP-CallHandlingOperations. It contains
-- only types concerning MAP-SEND-ROUTING-INFO (10.1) service.
EXPORTS
    sendRoutingInfo
;

IMPORTS
    OPERATION
FROM Remote-Operations-Information-Objects {
    joint-iso-itu-t remote-operations(4) informationObjects(5) version1(0)}

    systemFailure,
    dataMissing,
    unexpectedDataValue,
    facilityNotSupported,
    or-NotAllowed,
    unknownSubscriber,
    numberChanged,
    bearerServiceNotProvisioned,
    teleserviceNotProvisioned,
    absentSubscriber,
    busySubscriber,
    noSubscriberReply,
    callBarred,
    forwardingViolation,
    cug-Reject
FROM MAP-Errors {
   itu-t(0) identified-organization (4) etsi (0) mobileDomain (0)
   gsm-Network (1) modules (3) map-Errors (10) version10 (10)}

    SendRoutingInfoArg,
    SendRoutingInfoRes
FROM MAP-CH-DataTypes {
   itu-t(0) identified-organization (4) etsi (0) mobileDomain (0)
   gsm-Network (1) modules (3) map-CH-DataTypes (13) version10 (10)}
;

sendRoutingInfo  OPERATION ::= {	--Timer m
-- The timer is set to the upper limit of the range if the GMSC supports pre-paging.
    ARGUMENT	SendRoutingInfoArg
    RESULT	SendRoutingInfoRes
    ERRORS	{
	systemFailure |
	dataMissing |
	unexpectedDataValue |
	facilityNotSupported |
	or-NotAllowed |
	unknownSubscriber |
	numberChanged |
	bearerServiceNotProvisioned |
	teleserviceNotProvisioned |
	absentSubscriber |
	busySubscriber |
	noSubscriberReply |
	callBarred |
	cug-Reject |
	forwardingViolation
    }
    CODE	local:22 
}

END -- 17.6.3	MAP-CallHandlingOperations-SRI
