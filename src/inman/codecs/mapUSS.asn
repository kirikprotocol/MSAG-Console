/* $Id$ */
/* ************************************************************************** *
 * This file contains ASN.1 definitions for operations of                     *
 * MAP-PROCESS-UNSTRUCTURED-SS-REQUEST (11.9) service                         *
 * ************************************************************************** *
 * Author: R.V. Gerasimov						      *
 * -- 3GPP TS 29.002 V7.2.0 (2005-12)					      *
 * ************************************************************************** */

/* MAP-USS:
 *
 * networkUnstructuredSsContext-v2 APPLICATION-CONTEXT ::= { 
 * -- Responder is HLR, Initiator is VLR
 * -- Responder is VLR, Initiator is HLR
 * -- Responder is gsmSCF, Initiator is HLR
 * -- Responder is HLR, Initiator is gsmSCF
 * -- Responder is HLR, Initiator is HLR
 * OPERATIONS OF { unstructuredSsPackage-v2} -- &Symmetric
 * ID {map-ac networkUnstructuredSs(19) version2(2)} }
 *
 * where the unstructuredSsPackage-v2 is defined as:
 *
 * unstructuredSsPackage-v2 OPERATION-PACKAGE ::= {
 * -- Supplier is HLR if Consumer is VLR
 * -- Supplier is gsmSCF or HLR if Consumer is HLR
 * CONSUMER INVOKES { processUnstructuredSS-Request }
 * SUPPLIER INVOKES { unstructuredSS-Request | unstructuredSS-Notify} }
 *
 * The APPLICATION-CONTEXT is defined as:
 *
 * APPLICATION-CONTEXT ::= CLASS {
 *   &Symmetric		 OPERATION-PACKAGE OPTIONAL,
 *   &InitiatorConsumerOf OPERATION-PACKAGE OPTIONAL,
 *   &ResponderConsumerOf OPERATION-PACKAGE OPTIONAL,
 *   &code		 OBJECT IDENTIFIER
 * } WITH SYNTAX {
 *  [ OPERATIONS OF		&Symmetric ]
 *  [ INITIATOR CONSUMER OF	&InitiatorConsumerOf
 *      RESPONDER CONSUMER OF	&ResponderConsumerOf ]
 *   ID &code 
 * }
 * ************************************************************************** */

INMan-mapUSS-OIDs
DEFINITIONS ::=
-- GVRoman's NOTE: This module is for informative purposes only. 
-- It denotes OIDs of modules used by mapUSS service.
-- These OIDs are never used in below notation because of 
-- SourceForge's asn1c unable to parse ASN.1 module references
-- with named OID.
BEGIN
-- ******************************************************************* --
-- ROS modules follow
-- ******************************************************************* --
id-ros-InformationObjects OBJECT IDENTIFIER ::= {
    joint-iso-itu-t remote-operations(4) informationObjects(5) version1(0) }

-- ******************************************************************* --
-- MAP modules follow
-- ******************************************************************* --

-- 17.6.6 Errors
id-map-Errors OBJECT IDENTIFIER ::= {
    itu-t(0) identified-organization (4) etsi (0) mobileDomain (0)
    gsm-Network (1) modules (3) map-Errors (10) version10 (10)}

-- 17.7.1 Mobile Service data types
id-map-MS-DataTypes OBJECT IDENTIFIER ::= {
    itu-t identified-organization(4) etsi(0) mobileDomain(0)
    gsm-Network(1) modules(3) map-MS-DataTypes(11) version10(10) }

-- 17.7.4 Supplementary service data types
id-map-SS-DataTypes  OBJECT IDENTIFIER ::= {
    itu-t(0) identified-organization (4) etsi (0) mobileDomain (0)
    gsm-Network (1) modules (3) map-SS-DataTypes (14) version10 (10) }

-- 17.7.5 Supplementary service codes
id-map-SS-Code OBJECT IDENTIFIER ::= {
   itu-t(0) identified-organization (4) etsi (0) mobileDomain (0)
   gsm-Network (1) modules (3) map-SS-Code (15) version10 (10) }

-- 17.7.7 Error data types
id-map-ER-DataTypes OBJECT IDENTIFIER ::= {
   itu-t(0) identified-organization (4) etsi (0) mobileDomain (0)
   gsm-Network (1) modules (3) map-ER-DataTypes (17) version10 (10) }

-- 17.7.8 Common data types
id-map-CommonDataTypes OBJECT IDENTIFIER ::= {
    itu-t(0) identified-organization(4) etsi(0) mobileDomain(0) gsm-Network(1)
    modules(3) map-CommonDataTypes(18) version10(10) }

-- 17.7.11 Extension data types
id-map-Extension-DataTypes OBJECT IDENTIFIER ::= {
    itu-t identified-organization(4) etsi(0) mobileDomain(0) gsm-Network(1)
    modules(3) map-ExtensionDataTypes(21) version10(10) }

END -- INMan-mapUSS-OIDs

-- ******************************************************************* --
-- MAP modules follow
-- ******************************************************************* --

-- 17.6.4 Supplementary service operations
MAP-SupplementaryServiceOperations-USS {
    itu-t(0) identified-organization(4) etsi(0) mobileDomain(0)
    gsm-Network(1) modules(3) map-SupplementaryServiceOperations(8) version10(10) uss(9) }
DEFINITIONS IMPLICIT TAGS ::= BEGIN
-- NOTE: This module is excerpt from MAP-SupplementaryServiceOperations. It contains
-- only types concerning MAP-PROCESS-UNSTRUCTURED-SS-REQUEST (11.9) service.
IMPORTS
    Code, OPERATION, ERROR
FROM Remote-Operations-Information-Objects {
    joint-iso-itu-t remote-operations(4) informationObjects(5) version1(0) }

    systemFailure, unknownAlphabet,
    dataMissing, unexpectedDataValue, callBarred 
FROM MAP-Errors {
    itu-t(0) identified-organization (4) etsi (0) mobileDomain (0)
    gsm-Network (1) modules (3) map-Errors (10) version10 (10)}

    USSD-Arg, USSD-Res
FROM MAP-SS-DataTypes {
    itu-t(0) identified-organization (4) etsi (0) mobileDomain (0)
    gsm-Network (1) modules (3) map-SS-DataTypes (14) version10 (10)}
;


opcode-processUSS-Request Code ::= local : 59
-- opcode-USS-Request Code ::= local : 60
-- opcode-USS-Notify Code ::= local : 61

-- Errors for processUnstructuredSS-Request operation
ProcessUSS-RequestErrors ERROR ::= {
    systemFailure | dataMissing | unexpectedDataValue |
    unknownAlphabet | callBarred 
}

-- This service is used between the MSC and the VLR, between the VLR and the HLR,
-- between the HLR and gsmSCF and between the HLR and HLR to relay information in
-- order to allow unstructured supplementary service operation.
processUnstructuredSS-Request OPERATION ::= {
    ARGUMENT	USSD-Arg
    RESULT	USSD-Res
    ERRORS	{ ProcessUSS-RequestErrors }
    CODE	opcode-processUSS-Request
}

END -- end of MAP-SupplementaryServiceOperations
