/* $Id$ */
/* ************************************************************************** *
 * This file contains ASN.1 definitions of cap3SMS CONTRACT OPERATIONs        *
 * utilized by IN-Manager					              *
 * ************************************************************************** *
 * Author: R.V. Gerasimov						      *
 * ************************************************************************** */
INMan-cap3SMS-OIDs
DEFINITIONS ::=
-- GVRoman's NOTE: This module is for informative purposes only. 
-- It denotes OIDs of modules used by cap3SMS service.
-- These OIDs are never used in below notation because of 
-- SourceForge's asn1c unable to parse ASN.1 module references
-- with named OID.
BEGIN
-- ******************************************************************* --
-- ROS modules follow
-- ******************************************************************* --
id-ros-InformationObjects OBJECT IDENTIFIER ::= {
    joint-iso-itu-t remote-operations(4) informationObjects(5) version1(0) }

-- ******************************************************************* --
-- MAP modules follow
-- ******************************************************************* --
-- 17.7.1 Mobile Service data types
id-map-MS-DataTypes OBJECT IDENTIFIER ::= {
    itu-t(0) identified-organization(4) etsi(0) mobileDomain(0)
    gsm-Network(1) modules(3) map-MS-DataTypes(11) version10(10) }

-- 17.7.3 Call handling data types
id-map-CH-DataTypes OBJECT IDENTIFIER ::= {
    itu-t(0) identified-organization(4) etsi(0) mobileDomain(0)
      gsm-Network(1) modules(3) map-CH-DataTypes(13) version10(10) }

-- 17.7.8 Common data types
id-map-CommonDataTypes OBJECT IDENTIFIER ::= {
    itu-t(0) identified-organization(4) etsi(0) mobileDomain(0) gsm-Network(1)
    modules(3) map-CommonDataTypes(18) version10(10) }

-- 17.7.11 Extension data types    
id-map-ExtensionDataTypes OBJECT IDENTIFIER ::= {
    itu-t identified-organization(4) etsi(0) mobileDomain(0) gsm-Network(1)
    modules(3) map-ExtensionDataTypes(21) version10(10) }

-- ******************************************************************* --
-- INAP modules follow
-- ******************************************************************* --
id-cs1-DataTypes OBJECT IDENTIFIER ::= {
    itu-t(0) identified-organization(4) etsi(0) inDomain(1)
    in-network(1) modules(0) cs1-datatypes(2) version1(0) }

id-in-CS2-datatypes OBJECT IDENTIFIER ::= {
    itu-t(0) identified-organization(4) etsi(0) inDomain(1)
    in-network(1) cs2(20) modules(0) in-cs2-datatypes(0) version1(0) }

-- ******************************************************************* --
-- CAP modules follow
-- ******************************************************************* --
-- 5.1	Common Data types
id-cap-datatypes OBJECT IDENTIFIER ::= {
    itu-t(0) identified-organization(4) etsi(0) mobileDomain(0)
    umts-network(1) modules(3) cap-datatypes(52) version4(3) }

-- 5.2	Error types
id-cap-errortypes OBJECT IDENTIFIER ::= {
    itu-t(0) identified-organization(4) etsi(0) mobileDomain(0) umts-network(1)
    modules(3) cap-errortypes(51) version4(3) }

-- 5.3	Operation codes
id-cap-operationcodes OBJECT IDENTIFIER ::= {
    itu-t(0) identified-organization(4) etsi(0) mobileDomain(0) umts-network(1)
    modules(3) cap-operationcodes(53) version5(4) }

-- 5.4 Error codes
id-cap-errorcodes OBJECT IDENTIFIER ::= {
    itu-t(0) identified-organization(4) etsi(0) mobileDomain(0) umts-network(1)
    modules(3) cap-errorcodes(57) version4(3) }

-- 7.1	SMS operations and arguments
id-cap-SMS-ops-args {
    itu-t(0) identified-organization(4) etsi(0) mobileDomain(0) umts-network(1)
    modules(3) cap-SMS-ops-args(105) version5(4)}

END -- IN-Maneger-OIDs
