/* $Id$ */
/* ************************************************************************** *
 * This file contains ASN.1 definitions for operations of                     *
 * MAP-ANY-TIME-SUBSCRIPTION-INTERROGATION (8.11.3) service                   *
 * ************************************************************************** *
 * Author: R.V. Gerasimov						      *
 * -- 3GPP TS 29.002 V7.2.0 (2005-12)					      *
 * ************************************************************************** */

/* MAP-ATSI:
 *
 * anyTimeInfohandlingContext-v3 APPLICATION-CONTEXT ::= {
 *    -- Responder is HLR if Initiator is gsmSCF
 *    INITIATOR CONSUMER OF {
 *	anyTimeInformationHandlingPackage-v3
 *    }
 *    ID {map-ac anyTimeInfoHandling(43) version3(3)} 
 * }
 * 
 * This operation package includes the operations required for any time
 * information handling procedures between gsmSCF and HLR.
 * 
 * anyTimeInformationHandlingPackage-v3  OPERATION-PACKAGE ::= {
 *     -- Supplier is HLR if Consumer is gsmSCF
 *     CONSUMER INVOKES {
 * 	anyTimeSubscriptionInterrogation
 * 	| anyTimeModification -- not used by INMan
 *     } 
 * }
 */

INMan-mapATIH-OIDs
DEFINITIONS ::=
-- GVRoman's NOTE: This module is for informative purposes only. 
-- It denotes OIDs of modules used by mapATIH service.
-- These OIDs are never used in below notation because of 
-- SourceForge's asn1c unable to parse ASN.1 module references
-- with named OID.
BEGIN
-- ******************************************************************* --
-- ROS modules follow
-- ******************************************************************* --
id-ros-InformationObjects OBJECT IDENTIFIER ::= {
    joint-iso-itu-t remote-operations(4) informationObjects(5) version1(0) }

-- ******************************************************************* --
-- MAP modules follow
-- ******************************************************************* --

-- 17.6.6 Errors
id-map-Errors OBJECT IDENTIFIER ::= {
    itu-t(0) identified-organization (4) etsi (0) mobileDomain (0)
    gsm-Network (1) modules (3) map-Errors (10) version10 (10)}

-- 17.7.1 Mobile Service data types
id-map-MS-DataTypes OBJECT IDENTIFIER ::= {
    itu-t identified-organization(4) etsi(0) mobileDomain(0)
    gsm-Network(1) modules(3) map-MS-DataTypes(11) version10(10) }

-- 17.7.4 Supplementary service data types
id-map-SS-DataTypes  OBJECT IDENTIFIER ::= {
    itu-t(0) identified-organization (4) etsi (0) mobileDomain (0)
    gsm-Network (1) modules (3) map-SS-DataTypes (14) version10 (10) }

-- 17.7.5 Supplementary service codes
id-map-SS-Code OBJECT IDENTIFIER ::= {
   itu-t(0) identified-organization (4) etsi (0) mobileDomain (0)
   gsm-Network (1) modules (3) map-SS-Code (15) version10 (10) }

-- 17.7.7	Error data types
id-map-ER-DataTypes OBJECT IDENTIFIER ::= {
   itu-t(0) identified-organization (4) etsi (0) mobileDomain (0)
   gsm-Network (1) modules (3) map-ER-DataTypes (17) version10 (10) }

-- 17.7.8 Common data types
id-map-CommonDataTypes OBJECT IDENTIFIER ::= {
    itu-t(0) identified-organization(4) etsi(0) mobileDomain(0) gsm-Network(1)
    modules(3) map-CommonDataTypes(18) version10(10) }

-- 17.7.9 Teleservice Codes
id-map-TS-Code  OBJECT IDENTIFIER ::= {
    itu-t(0) identified-organization (4) etsi (0) mobileDomain (0)
    gsm-Network (1) modules (3) map-TS-Code (19) version10 (10) }

-- 17.7.10 Bearer Service Codes
id-map-BS-Code  OBJECT IDENTIFIER ::= {
    itu-t(0) identified-organization (4) etsi (0) mobileDomain (0)
    gsm-Network (1) modules (3) map-BS-Code (20) version10 (10) }

-- 17.7.11 Extension data types
id-map-Extension-DataTypes OBJECT IDENTIFIER ::= {
    itu-t identified-organization(4) etsi(0) mobileDomain(0) gsm-Network(1)
    modules(3) map-ExtensionDataTypes(21) version10(10) }

END -- INMan-mapATIH-OIDs


-- 17.6   MAP operations and errors
-- 17.6.1 Mobile Service Operations
MAP-MobileServiceOperations-ATIH {
   itu-t(0) identified-organization (4) etsi (0) mobileDomain (0)
   gsm-Network (1) modules (3) map-MobileServiceOperations (5) version10 (10)
   atih(3) -- 8.11.3 -- }
DEFINITIONS ::= BEGIN
-- NOTE: This module is excerpt from MAP-MobileServiceOperations. It contains
-- only types concerning MAP-ANY-TIME-SUBSCRIPTION-INTERROGATION service.
EXPORTS
    -- any time information handling operations
    anyTimeSubscriptionInterrogation
;

IMPORTS
    OPERATION, ERROR
FROM Remote-Operations-Information-Objects {
    joint-iso-itu-t remote-operations(4) informationObjects(5) version1(0)}

    dataMissing,
    unexpectedDataValue,
    unknownSubscriber,
    atsi-NotAllowed,
    bearerServiceNotProvisioned,
    teleserviceNotProvisioned,
    callBarred,
    illegalSS-Operation,
    ss-NotAvailable,
    informationNotAvailable
FROM MAP-Errors {
   itu-t(0) identified-organization (4) etsi (0) mobileDomain (0)
   gsm-Network (1) modules (3) map-Errors (10) version10 (10)}

    AnyTimeSubscriptionInterrogationArg,
    AnyTimeSubscriptionInterrogationRes
FROM MAP-MS-DataTypes-ATIH {
   itu-t(0) identified-organization (4) etsi (0) mobileDomain (0)
   gsm-Network (1) modules (3) map-MS-DataTypes (11) version10 (10) atih(3) }
;

ATSI-BasicErrors ERROR ::= {
    dataMissing |
    unexpectedDataValue |
    unknownSubscriber |
    bearerServiceNotProvisioned |
    teleserviceNotProvisioned |
    callBarred |
    informationNotAvailable |
    illegalSS-Operation
}

-- any time information handling operations
anyTimeSubscriptionInterrogation  OPERATION ::= { -- Timer m
    ARGUMENT	AnyTimeSubscriptionInterrogationArg
    RESULT	AnyTimeSubscriptionInterrogationRes
    ERRORS	{ ATSI-BasicErrors | atsi-NotAllowed | ss-NotAvailable }
    CODE	local:62 
}
END -- 17.6.1 MAP-MobileServiceOperations
 
 
-- 17.7   MAP constants and data types
-- 17.7.1 Mobile Service data types
MAP-MS-DataTypes-ATIH {
   itu-t(0) identified-organization (4) etsi (0) mobileDomain (0)
   gsm-Network (1) modules (3) map-MS-DataTypes (11) version10 (10)
   atih(3) -- 8.11.3 -- }
DEFINITIONS IMPLICIT TAGS ::= BEGIN
-- NOTE: This module is excerpt from MAP-MobileServiceOperations. It contains
-- only types concerning MAP-ANY-TIME-SUBSCRIPTION-INTERROGATION service.
EXPORTS
-- subscriber management types
--    ODB-Data,
--    SS-CSI,
-- any time information handling types
    AnyTimeSubscriptionInterrogationArg,
    AnyTimeSubscriptionInterrogationRes
;

IMPORTS
    SS-ForBS-Code, Password
FROM MAP-SS-DataTypes {
   itu-t(0) identified-organization (4) etsi (0) mobileDomain (0)
   gsm-Network (1) modules (3) map-SS-DataTypes (14) version10 (10)}

    SS-Code
FROM MAP-SS-Code {
   itu-t(0) identified-organization (4) etsi (0) mobileDomain (0)
   gsm-Network (1) modules (3) map-SS-Code (15) version10 (10)}

    AddressString,
    ISDN-AddressString, 
    ISDN-SubaddressString, 
    FTN-AddressString,
    IMSI, 
    Ext-SS-Status,
    Ext-BasicServiceCode,
    SubscriberIdentity
FROM MAP-CommonDataTypes {
   itu-t(0) identified-organization (4) etsi (0) mobileDomain (0)
   gsm-Network (1) modules (3) map-CommonDataTypes (18) version10 (10)}

    ExtensionContainer
FROM MAP-ExtensionDataTypes {
   itu-t(0) identified-organization (4) etsi (0) mobileDomain (0)
   gsm-Network (1) modules (3) map-ExtensionDataTypes (21) version10 (10)}

    O-CSI, 
    D-CSI,
    O-BcsmCamelTDPCriteriaList, 
    T-BCSM-CAMEL-TDP-CriteriaList,
    ServiceKey,
    DefaultCallHandling,
    CamelCapabilityHandling,
    BasicServiceCriteria,
    SupportedCamelPhases,
    OfferedCamel4CSIs,
    maxNumOfCamelTDPData,
    T-CSI,
    T-BcsmTriggerDetectionPoint
FROM MAP-MS-DataTypes {
   itu-t(0) identified-organization (4) etsi (0) mobileDomain (0)
   gsm-Network (1) modules (3) map-MS-DataTypes (11) version10 (10)}
;

GPRS-CSI ::= SEQUENCE {
    gprs-CamelTDPDataList	[0] GPRS-CamelTDPDataList	OPTIONAL,
    camelCapabilityHandling	[1] CamelCapabilityHandling	OPTIONAL,
    extensionContainer		[2] ExtensionContainer	OPTIONAL,
    notificationToCSE		[3] NULL		OPTIONAL,
    csi-Active			[4] NULL		OPTIONAL,
    ...
}
-- notificationToCSE and csi-Active shall not be present when GPRS-CSI is sent to SGSN.
-- They may only be included in ATSI/ATM ack/NSDC message. 
-- GPRS-CamelTDPData and  camelCapabilityHandling shall be present in 
-- the GPRS-CSI sequence.
-- If GPRS-CSI is segmented, gprs-CamelTDPDataList and camelCapabilityHandling shall be 
-- present in the first segment

GPRS-CamelTDPDataList ::= SEQUENCE SIZE (1..maxNumOfCamelTDPData) OF
			    GPRS-CamelTDPData
-- GPRS-CamelTDPDataList shall not contain more than one instance of
-- GPRS-CamelTDPData containing the same value for gprs-TriggerDetectionPoint.

GPRS-CamelTDPData ::= SEQUENCE {
    gprs-TriggerDetectionPoint	[0] GPRS-TriggerDetectionPoint,
    serviceKey			[1] ServiceKey,
    gsmSCF-Address		[2] ISDN-AddressString,
    defaultSessionHandling	[3] DefaultGPRS-Handling,
    extensionContainer		[4] ExtensionContainer	OPTIONAL,
    ...
}

DefaultGPRS-Handling ::= ENUMERATED {
    continueTransaction (0), releaseTransaction (1), ...
}
-- exception handling:
-- reception of values in range 2-31 shall be treated as "continueTransaction"
-- reception of values greater than 31 shall be treated as "releaseTransaction"

GPRS-TriggerDetectionPoint ::= ENUMERATED {
    attach(1), attachChangeOfPosition(2), pdp-ContextEstablishment(11),
    pdp-ContextEstablishmentAcknowledgement(12), pdp-ContextChangeOfPosition(14),
    ... 
}
-- exception handling:
-- For GPRS-CamelTDPData sequences containing this parameter with any
-- other value than the ones listed the receiver shall ignore the whole 
-- GPRS-CamelTDPDatasequence.

ODB-Data ::= SEQUENCE {
    odb-GeneralData	ODB-GeneralData,
    odb-HPLMN-Data	ODB-HPLMN-Data	OPTIONAL,
    extensionContainer	ExtensionContainer	OPTIONAL,
    ...
}

ODB-GeneralData ::= BIT STRING {
    allOG-CallsBarred  (0),
    internationalOGCallsBarred  (1),
    internationalOGCallsNotToHPLMN-CountryBarred  (2),
    interzonalOGCallsBarred (6),
    interzonalOGCallsNotToHPLMN-CountryBarred (7),
    interzonalOGCallsAndInternationalOGCallsNotToHPLMN-CountryBarred (8),
    premiumRateInformationOGCallsBarred  (3),
    premiumRateEntertainementOGCallsBarred  (4),
    ss-AccessBarred  (5),
    allECT-Barred (9),
    chargeableECT-Barred (10),
    internationalECT-Barred (11),
    interzonalECT-Barred (12),
    doublyChargeableECT-Barred (13),
    multipleECT-Barred (14),
    allPacketOrientedServicesBarred (15),
    roamerAccessToHPLMN-AP-Barred  (16),
    roamerAccessToVPLMN-AP-Barred  (17),
    roamingOutsidePLMNOG-CallsBarred  (18),
    allIC-CallsBarred  (19),
    roamingOutsidePLMNIC-CallsBarred  (20),
    roamingOutsidePLMNICountryIC-CallsBarred  (21),
    roamingOutsidePLMN-Barred  (22),
    roamingOutsidePLMN-CountryBarred  (23),
    registrationAllCF-Barred  (24),
    registrationCFNotToHPLMN-Barred  (25),
    registrationInterzonalCF-Barred  (26),
    registrationInterzonalCFNotToHPLMN-Barred  (27),
    registrationInternationalCF-Barred  (28)
} (SIZE (15..32))
-- exception handling: reception of unknown bit assignments in the
-- ODB-GeneralData type shall be treated like unsupported ODB-GeneralData
-- When the ODB-GeneralData type is removed from the HLR for a given subscriber, 
-- in NoteSubscriberDataModified operation sent toward the gsmSCF 
-- all bits shall be set to "O".

ODB-HPLMN-Data ::= BIT STRING {
    plmn-SpecificBarringType1  (0),
    plmn-SpecificBarringType2  (1),
    plmn-SpecificBarringType3  (2),
    plmn-SpecificBarringType4  (3)
} (SIZE (4..32))
-- exception handling: reception of unknown bit assignments in the
-- ODB-HPLMN-Data type shall be treated like unsupported ODB-HPLMN-Data 
-- When the ODB-HPLMN-Data type is removed from the HLR for a given subscriber, 
-- in NoteSubscriberDataModified operation sent toward the gsmSCF
-- all bits shall be set to "O".

Ext-ForwFeatureList ::= SEQUENCE SIZE (1..maxNumOfExt-BasicServiceGroups) OF
				Ext-ForwFeature

Ext-ForwFeature ::= SEQUENCE {
    basicService		Ext-BasicServiceCode	OPTIONAL,
    ss-Status			[4] Ext-SS-Status,
    forwardedToNumber		[5] ISDN-AddressString	OPTIONAL,
-- When this data type is sent from an HLR which supports CAMEL Phase 2
-- to a VLR that supports CAMEL Phase 2 the VLR shall not check the
-- format of the number
    forwardedToSubaddress	[8] ISDN-SubaddressString	OPTIONAL,
    forwardingOptions		[6] Ext-ForwOptions	OPTIONAL,
    noReplyConditionTime	[7] Ext-NoRepCondTime	OPTIONAL,
    extensionContainer		[9] ExtensionContainer	OPTIONAL,
    ...,
    longForwardedToNumber	[10] FTN-AddressString	OPTIONAL
}

Ext-ForwOptions ::= OCTET STRING (SIZE (1..5))
-- OCTET 1:
--  bit 8: notification to forwarding party
--	0  no notification
--	1  notification
--  bit 7: redirecting presentation
--	0 no presentation  
--	1  presentation
--  bit 6: notification to calling party
--	0  no notification
--	1  notification
--  bit 5: 0 (unused)
--  bits 43: forwarding reason
--	00  ms not reachable
--	01  ms busy
--	10  no reply
--	11  unconditional
-- bits 21: 00 (unused)

-- OCTETS 2-5: reserved for future use. They shall be discarded if
-- received and not understood.

Ext-NoRepCondTime ::= INTEGER (1..100)
-- Only values 5-30 are used.
-- Values in the ranges 1-4 and 31-100 are reserved for future use
-- If received:
--		values 1-4 shall be mapped on to value 5
--		values 31-100 shall be mapped on to value 30

Ext-CallBarFeatureList ::= SEQUENCE SIZE (1..maxNumOfExt-BasicServiceGroups) OF
				Ext-CallBarringFeature

Ext-CallBarringFeature ::= SEQUENCE {
    basicService	Ext-BasicServiceCode	OPTIONAL,
    ss-Status		[4] Ext-SS-Status,
    extensionContainer	ExtensionContainer	OPTIONAL,
    ...
}
maxNumOfExt-BasicServiceGroups  INTEGER ::= 32

SpecificCSI-Withdraw ::= BIT STRING {
    o-csi (0), ss-csi (1), tif-csi (2), d-csi (3),
    vt-csi (4), mo-sms-csi (5), m-csi (6), gprs-csi (7),
    t-csi (8), mt-sms-csi (9), mg-csi (10), o-IM-CSI (11), 
    d-IM-CSI (12), vt-IM-CSI (13) 
} (SIZE(8..32)) 
-- exception handling:
-- bits 11 to 31 shall be ignored if received by a non-IP Multimedia Core Network entity.
-- bits 0-10 and 14-31 shall be ignored if received by an IP Multimedia Core Network entity.
-- bits 11-13 are only applicable in an IP Multimedia Core Network.
-- Bit 8 and bits 11-13 are only applicable for the NoteSubscriberDataModified operation.

MT-smsCAMELTDP-CriteriaList ::= SEQUENCE SIZE (1.. maxNumOfCamelTDPData) OF
				    MT-smsCAMELTDP-Criteria

MT-smsCAMELTDP-Criteria ::= SEQUENCE {
    sms-TriggerDetectionPoint	SMS-TriggerDetectionPoint,
    tpdu-TypeCriterion		[0] TPDU-TypeCriterion	OPTIONAL,
    ... 
}

TPDU-TypeCriterion ::= SEQUENCE SIZE (1..maxNumOfTPDUTypes) OF MT-SMS-TPDU-Type
maxNumOfTPDUTypes INTEGER ::= 5

MT-SMS-TPDU-Type ::= ENUMERATED {
    sms-DELIVER(0), sms-SUBMIT-REPORT(1), sms-STATUS-REPORT (2), ... 
}
-- exception handling:
-- For TPDU-TypeCriterion sequences containing this parameter with any
-- other value than the ones listed above the receiver shall ignore 
-- the whole TPDU-TypeCriterion sequence.
-- In CAMEL phase 4, sms-SUBMIT-REPORT shall not be used and a received TPDU-TypeCriterion
-- sequence containing sms-SUBMIT-REPORT shall be wholly ignored.

SS-CSI ::= SEQUENCE {
    ss-CamelData	SS-CamelData,
    extensionContainer	ExtensionContainer	OPTIONAL,
    ...,
    notificationToCSE	[0] NULL	OPTIONAL,
    csi-Active		[1] NULL	OPTIONAL
-- notificationToCSE and csi-Active shall not be present when SS-CSI is sent to VLR.
-- They may only be included in ATSI/ATM ack/NSDC message.
}

SS-CamelData  ::= SEQUENCE {
    ss-EventList	SS-EventList,
    gsmSCF-Address	ISDN-AddressString,
    extensionContainer	[0] ExtensionContainer	OPTIONAL, 
    ...
}

SS-EventList  ::= SEQUENCE SIZE (1..maxNumOfCamelSSEvents) OF SS-Code
-- Actions for the following SS-Code values are defined in CAMEL Phase 3:
-- ect		SS-Code ::= '00110001'B
-- multiPTY	SS-Code ::= '01010001'B
-- cd		SS-Code ::= '00100100'B
-- ccbs		SS-Code ::= '01000100'B
-- all other SS codes shall be ignored
-- When SS-CSI is sent to the VLR, it shall not contain a marking for ccbs.
-- If the VLR receives SS-CSI containing a marking for ccbs, the VLR shall discard the
-- ccbs marking in SS-CSI.
maxNumOfCamelSSEvents INTEGER ::= 10

SMS-CSI ::= SEQUENCE {
    sms-CAMEL-TDP-DataList	[0] SMS-CAMEL-TDP-DataList	OPTIONAL,
    camelCapabilityHandling	[1] CamelCapabilityHandling	OPTIONAL,
    extensionContainer		[2] ExtensionContainer	OPTIONAL,
    notificationToCSE		[3] NULL		OPTIONAL,
    csi-Active			[4] NULL		OPTIONAL,
    ...
}
-- notificationToCSE and csi-Active shall not be present
-- when MO-SMS-CSI or MT-SMS-CSI is sent to VLR or SGSN.
-- They may only be included in ATSI/ATM ack/NSDC message.
-- SMS-CAMEL-TDP-Data and  camelCapabilityHandling shall be present in 
-- the SMS-CSI sequence.
-- If SMS-CSI is segmented, sms-CAMEL-TDP-DataList and camelCapabilityHandling shall be 
-- present in the first segment

SMS-CAMEL-TDP-DataList ::= SEQUENCE SIZE (1..maxNumOfCamelTDPData) OF
			    SMS-CAMEL-TDP-Data
-- SMS-CAMEL-TDP-DataList shall not contain more than one instance of
-- SMS-CAMEL-TDP-Data containing the same value for sms-TriggerDetectionPoint.

SMS-CAMEL-TDP-Data ::= SEQUENCE {
    sms-TriggerDetectionPoint	[0] SMS-TriggerDetectionPoint,
    serviceKey			[1] ServiceKey,
    gsmSCF-Address		[2] ISDN-AddressString,
    defaultSMS-Handling		[3] DefaultSMS-Handling,
    extensionContainer		[4] ExtensionContainer	OPTIONAL,
    ...
}

SMS-TriggerDetectionPoint ::= ENUMERATED {
    sms-CollectedInfo (1), ..., sms-DeliveryRequest (2)
}
-- exception handling:
-- For SMS-CAMEL-TDP-Data and MT-smsCAMELTDP-Criteria sequences containing this 
-- parameter with any other value than the ones listed the receiver shall ignore
-- the whole sequence.
--
-- If this parameter is received with any other value than sms-CollectedInfo
-- in an SMS-CAMEL-TDP-Data sequence contained in mo-sms-CSI, then the receiver shall
-- ignore the whole SMS-CAMEL-TDP-Data sequence.
--
-- If this parameter is received with any other value than sms-DeliveryRequest
-- in an SMS-CAMEL-TDP-Data sequence contained in mt-sms-CSI then the receiver shall
-- ignore the whole SMS-CAMEL-TDP-Data sequence.
--
-- If this parameter is received with any other value than sms-DeliveryRequest
-- in an MT-smsCAMELTDP-Criteria sequence then the receiver shall
-- ignore the whole MT-smsCAMELTDP-Criteria sequence.

DefaultSMS-Handling ::= ENUMERATED {
    continueTransaction (0), releaseTransaction (1), ...
}
-- exception handling:
-- reception of values in range 2-31 shall be treated as "continueTransaction"
-- reception of values greater than 31 shall be treated as "releaseTransaction"

M-CSI ::= SEQUENCE {
    mobilityTriggers	MobilityTriggers,
    serviceKey		ServiceKey,
    gsmSCF-Address	[0] ISDN-AddressString,
    extensionContainer	[1] ExtensionContainer	OPTIONAL,
    notificationToCSE	[2] NULL		OPTIONAL,
    csi-Active		[3] NULL		OPTIONAL,
    ...
}
--	notificationToCSE and csi-Active shall not be present when M-CSI is sent to VLR.
--	They may only be included in ATSI/ATM ack/NSDC message.

MG-CSI ::= SEQUENCE {
    mobilityTriggers	MobilityTriggers,
    serviceKey		ServiceKey,
    gsmSCF-Address	[0] ISDN-AddressString,
    extensionContainer	[1] ExtensionContainer	OPTIONAL,
    notificationToCSE	[2] NULL		OPTIONAL,
    csi-Active		[3] NULL		OPTIONAL,
    ...
}
--	notificationToCSE and csi-Active shall not be present when MG-CSI is sent to SGSN.
--	They may only be included in ATSI/ATM ack/NSDC message.

MobilityTriggers  ::= SEQUENCE SIZE (1..maxNumOfMobilityTriggers) OF MM-Code
maxNumOfMobilityTriggers INTEGER ::= 10

MM-Code ::= OCTET STRING (SIZE (1))
-- This type is used to indicate a Mobility Management event.
-- Actions for the following MM-Code values are defined in CAMEL Phase 4:
--
-- CS domain MM events:
-- Location-update-in-same-VLR	MM-Code ::= '00000000'B
-- Location-update-to-other-VLR	MM-Code ::= '00000001'B
-- IMSI-Attach	MM-Code ::= '00000010'B
-- MS-initiated-IMSI-Detach	MM-Code ::= '00000011'B
-- Network-initiated-IMSI-Detach	MM-Code ::= '00000100'B
--
-- PS domain MM events:
-- Routeing-Area-update-in-same-SGSN	MM-Code ::= '10000000'B
-- Routeing-Area-update-to-other-SGSN-update-from-new-SGSN
-- 			MM-Code ::= '10000001'B
-- Routeing-Area-update-to-other-SGSN-disconnect-by-detach
-- 			MM-Code ::= '10000010'B
-- GPRS-Attach	MM-Code ::= '10000011'B
-- MS-initiated-GPRS-Detach	MM-Code ::= '10000100'B
-- Network-initiated-GPRS-Detach	MM-Code ::= '10000101'B 
-- Network-initiated-transfer-to-MS-not-reachable-for-paging
-- 			MM-Code ::= '10000110'B
--
-- If the MSC receives any other MM-code than the ones listed above for the
-- CS domain, then the MSC shall ignore that MM-code.
-- If the SGSN receives any other MM-code than the ones listed above for the
-- PS domain, then the SGSN shall ignore that MM-code.

-- any time information handling types

AnyTimeSubscriptionInterrogationArg ::= SEQUENCE {
    subscriberIdentity		[0] SubscriberIdentity,
    requestedSubscriptionInfo	[1] RequestedSubscriptionInfo,
    gsmSCF-Address		[2] ISDN-AddressString,
    extensionContainer		[3] ExtensionContainer	OPTIONAL,
    longFTN-Supported		[4] NULL		OPTIONAL,
    ...
} --<PDU>--

AnyTimeSubscriptionInterrogationRes ::= SEQUENCE {
    callForwardingData		[1] CallForwardingData	OPTIONAL,
    callBarringData		[2] CallBarringData	OPTIONAL,
    odb-Info			[3] ODB-Info	OPTIONAL,
    camel-SubscriptionInfo	[4] CAMEL-SubscriptionInfo	OPTIONAL,
    supportedVLR-CAMEL-Phases	[5] SupportedCamelPhases	OPTIONAL,
    supportedSGSN-CAMEL-Phases	[6] SupportedCamelPhases	OPTIONAL,
    extensionContainer		[7] ExtensionContainer	OPTIONAL,
    ... ,
    offeredCamel4CSIsInVLR	[8] OfferedCamel4CSIs	OPTIONAL,
    offeredCamel4CSIsInSGSN	[9] OfferedCamel4CSIs	OPTIONAL
} --<PDU>--

RequestedSubscriptionInfo ::= SEQUENCE {
    requestedSS-Info		[1] SS-ForBS-Code	OPTIONAL,
    odb				[2] NULL		OPTIONAL,
    requestedCAMEL-SubscriptionInfo
				[3] RequestedCAMEL-SubscriptionInfo	OPTIONAL,
    supportedVLR-CAMEL-Phases	[4] NULL		OPTIONAL,
    supportedSGSN-CAMEL-Phases	[5] NULL		OPTIONAL,
    extensionContainer		[6] ExtensionContainer	OPTIONAL,
    ...,
    additionalRequestedCAMEL-SubscriptionInfo
				[7] AdditionalRequestedCAMEL-SubscriptionInfo
							OPTIONAL 
}

RequestedCAMEL-SubscriptionInfo ::= ENUMERATED {
    o-CSI(0), t-CSI(1), vt-CSI(2), tif-CSI(3), gprs-CSI(4),
    mo-sms-CSI(5), ss-CSI(6), m-CSI(7), d-csi(8)
}

AdditionalRequestedCAMEL-SubscriptionInfo ::= ENUMERATED {
    mt-sms-CSI	(0), mg-csi(1), o-IM-CSI(2),
    d-IM-CSI(3), vt-IM-CSI(4), ...
}
-- exception handling: unknown values shall be discarded by the receiver.

CallForwardingData ::= SEQUENCE {
    forwardingFeatureList	Ext-ForwFeatureList,
    notificationToCSE		NULL			OPTIONAL,
    extensionContainer		[0] ExtensionContainer	OPTIONAL,
    ...
}

CallBarringData ::= SEQUENCE {
    callBarringFeatureList		Ext-CallBarFeatureList,
    password				Password		OPTIONAL,
    wrongPasswordAttemptsCounter	WrongPasswordAttemptsCounter	OPTIONAL,
    notificationToCSE			NULL			OPTIONAL,
    extensionContainer			ExtensionContainer	OPTIONAL,
    ...
}
WrongPasswordAttemptsCounter ::= INTEGER (0..4)

ODB-Info ::= SEQUENCE {
    odb-Data		ODB-Data,
    notificationToCSE	NULL			OPTIONAL,
    extensionContainer	ExtensionContainer	OPTIONAL,
    ...
}

CAMEL-SubscriptionInfo ::= SEQUENCE {
    o-CSI			[0] O-CSI		OPTIONAL,
    o-BcsmCamelTDP-CriteriaList	[1] O-BcsmCamelTDPCriteriaList	OPTIONAL, 
    d-CSI			[2] D-CSI		OPTIONAL,
    t-CSI			[3] T-CSI		OPTIONAL,
    t-BCSM-CAMEL-TDP-CriteriaList	[4] T-BCSM-CAMEL-TDP-CriteriaList	OPTIONAL,
    vt-CSI			[5] T-CSI		OPTIONAL,
    vt-BCSM-CAMEL-TDP-CriteriaList	[6] T-BCSM-CAMEL-TDP-CriteriaList	OPTIONAL,
    tif-CSI			[7] NULL		OPTIONAL,
    tif-CSI-NotificationToCSE	[8] NULL		OPTIONAL,
    gprs-CSI			[9] GPRS-CSI	OPTIONAL,
    mo-sms-CSI			[10] SMS-CSI		OPTIONAL,
    ss-CSI			[11] SS-CSI		OPTIONAL,
    m-CSI			[12] M-CSI		OPTIONAL,
    extensionContainer		[13] ExtensionContainer	OPTIONAL,
    ...,
    specificCSIDeletedList	[14] SpecificCSI-Withdraw	OPTIONAL,
    mt-sms-CSI			[15] SMS-CSI		OPTIONAL,
    mt-smsCAMELTDP-CriteriaList	[16] MT-smsCAMELTDP-CriteriaList	OPTIONAL,
    mg-csi			[17] MG-CSI		OPTIONAL,
    o-IM-CSI			[18] O-CSI		OPTIONAL,
    o-IM-BcsmCamelTDP-CriteriaList	[19] O-BcsmCamelTDPCriteriaList	OPTIONAL,
    d-IM-CSI			[20] D-CSI		OPTIONAL,
    vt-IM-CSI			[21] T-CSI		OPTIONAL,
    vt-IM-BCSM-CAMEL-TDP-CriteriaList	[22] T-BCSM-CAMEL-TDP-CriteriaList	OPTIONAL
}
END -- 17.7.1 MAP-MS-DataTypes (Mobile Service data types)
