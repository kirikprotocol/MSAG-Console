/* ************************************************************************** *
 * @(#)$Id$
 * ************************************************************************** */
/* 17.6.7       Group Call operations
 * ************************************************************************** */
/* Author: R.V. Gerasimov                                                                             *
 * -- 3GPP TS 29.002 V7.15.0 (2010-06)                                                        *
 * ************************************************************************** */
MAP-Group-Call-Operations {
   itu-t(0) identified-organization (4) etsi (0) mobileDomain (0)
   gsm-Network (1) modules (3) map-Group-Call-Operations (22)
   version10 (10)}
DEFINITIONS ::=
BEGIN

EXPORTS
        prepareGroupCall,
        sendGroupCallEndSignal,
        forwardGroupCallSignalling,
        processGroupCallSignalling,
        sendGroupCallInfo
;

IMPORTS
        OPERATION
FROM Remote-Operations-Information-Objects {
    joint-iso-itu-t(0) remote-operations(4) informationObjects(5) version1(0)}

        systemFailure,
        unexpectedDataValue,
        noGroupCallNumberAvailable,
        ongoingGroupCall,
        unknownSubscriber,
        teleserviceNotProvisioned,
        dataMissing
FROM MAP-Errors {
   itu-t(0) identified-organization (4) etsi (0) mobileDomain (0)
   gsm-Network (1) modules (3) map-Errors (10) version10 (10)}

        PrepareGroupCallArg,
        PrepareGroupCallRes,
        SendGroupCallEndSignalArg,
        SendGroupCallEndSignalRes,
        ForwardGroupCallSignallingArg,
        ProcessGroupCallSignallingArg,
        SendGroupCallInfoArg,
        SendGroupCallInfoRes
FROM MAP-GR-DataTypes {
   itu-t(0) identified-organization (4) etsi (0) mobileDomain (0)
   gsm-Network (1) modules (3) map-GR-DataTypes (23) version10 (10)}
;

prepareGroupCall  OPERATION ::= {                               --Timer m
        ARGUMENT
                PrepareGroupCallArg
        RESULT
        PrepareGroupCallRes
        ERRORS {
                systemFailure |
                noGroupCallNumberAvailable |
                unexpectedDataValue}
        CODE    local:39 }

sendGroupCallEndSignal  OPERATION ::= {                         --Timer l
        ARGUMENT
                SendGroupCallEndSignalArg
        RESULT
                SendGroupCallEndSignalRes
        CODE    local:40 }

processGroupCallSignalling  OPERATION ::= {                             --Timer s
        ARGUMENT
                ProcessGroupCallSignallingArg
        CODE    local:41 }

forwardGroupCallSignalling  OPERATION ::= {                             --Timer s
        ARGUMENT
                ForwardGroupCallSignallingArg
        CODE    local:42 }

sendGroupCallInfo  OPERATION ::= {                              --Timer m
        ARGUMENT
                SendGroupCallInfoArg
        RESULT
                SendGroupCallInfoRes
        ERRORS {
                systemFailure |
                ongoingGroupCall |
                unexpectedDataValue |
                dataMissing |
                teleserviceNotProvisioned |
                unknownSubscriber}
        CODE    local:84 }

END
