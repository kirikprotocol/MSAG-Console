-- iso.org.dod.internet.private.enterprise (1.3.6.1.4.1)
-- .spelio.software.asn1c.test (9363.1.5.1)
-- .24

ModuleTestSequence
	{ iso org(3) dod(6) internet(1) private(4) enterprise(1)
		spelio(9363) software(1) asn1c(5) test(1) 24 }
	DEFINITIONS IMPLICIT TAGS ::=
BEGIN
        SeqType1 ::= SEQUENCE {
            a         INTEGER,
            b [5]     INTEGER,
            c [1]     NULL
        }

        SeqType2 ::= SEQUENCE {
            a         INTEGER,
            b [3]     INTEGER OPTIONAL,
            c [7]     INTEGER OPTIONAL
        }

        SeqType3 ::= SEQUENCE {
            a         INTEGER,
            b [3]     INTEGER OPTIONAL,
            ...
        }

        SeqType4 ::= SEQUENCE {
            a         INTEGER,
            b [3]     INTEGER OPTIONAL,
            ... ,
            c [4]     INTEGER OPTIONAL
        }

        maxCount  INTEGER ::= 5

        SeqOfType1 ::= SEQUENCE SIZE (1..maxCount) OF SeqType1

        ChoiceType1 ::= CHOICE {
           case1      INTEGER,
           case2      BOOLEAN
        }

        ChoiceType2 ::= [15] CHOICE {
           case1      INTEGER,
           case2      BOOLEAN
        }

        SeqType5 ::= SEQUENCE {
           a        ChoiceType1,
           b        ChoiceType2,
           c [10]   ChoiceType1,
           d [11]   ChoiceType2
        }
END
