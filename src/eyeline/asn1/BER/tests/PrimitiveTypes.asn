-- iso.org.dod.internet.private.enterprise (1.3.6.1.4.1)
-- .spelio.software.asn1c.test (9363.1.5.1)
-- .7

ModuleTestInt
	{ iso org(3) dod(6) internet (1) private(4) enterprise(1)
		spelio(9363) software(1) asn1c(5) test(1) 7 }
	DEFINITIONS ::=
BEGIN
	IntValue ::= INTEGER

        EnumValue ::= ENUMERATED
		{
                  red,  -- will be 0 --
                  green,  -- will be 1 --
                  blue(4),
                  alpha,
                  ... -- extensible --
		}

        BoolValue ::= BOOLEAN
        BitStrValue ::= BIT STRING
        OctsStrValue ::= OCTET STRING

--        OIDType  OBJECT IDENTIFIER ::= { 1 2 3 10000 }
--        OIDValue ::= OIDType
END
