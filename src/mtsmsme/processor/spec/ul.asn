MAP-MobileServiceOperations {
  itu-t identified-organization (4) etsi (0) mobileDomain (0)
  gsm-Network (1) modules (3) map-MobileServiceOperations (5)
  version9 (9)}
DEFINITIONS
::=
BEGIN
IMPORTS
  OPERATION, ERROR
FROM Remote-Operations-Information-Objects {
  joint-iso-itu-t remote-operations(4)
  informationObjects(5) version1(0)}

  UpdateLocationArg,
  UpdateLocationRes,
  InsertSubscriberDataArg
FROM MAP-MS-DataTypes {
    itu-t identified-organization (4) etsi (0) mobileDomain (0)
    gsm-Network (1) modules (3) map-MS-DataTypes (11) version9 (9)}

    systemFailure,
    dataMissing,
    unexpectedDataValue,
    unknownSubscriber,
    roamingNotAllowed
FROM MAP-Errors {
   itu-t identified-organization (4) etsi (0) mobileDomain (0)
   gsm-Network (1) modules (3) map-Errors (10) version10 (10)}

;
updateLocation OPERATION ::= {
    ARGUMENT
        UpdateLocationArg
    RESULT
        UpdateLocationRes
--    ERRORS {
--        systemFailure |
--        dataMissing |
--        unexpectedDataValue |
--        unknownSubscriber |
--        roamingNotAllowed
--    }
    CODE 
        local:2
}
cancelLocation OPERATION ::= { --Timer m
    ARGUMENT
	CancelLocationArg
    RESULT
	CancelLocationRes -- optional
    ERRORS {
	dataMissing |
	unexpectedDataValue
    }
    CODE
	local:3
}

insertSubscriberData OPERATION ::= { --Timer m
    ARGUMENT
	InsertSubscriberDataArg
    RESULT
	InsertSubscriberDataRes -- optional
    ERRORS {
	dataMissing |
	unexpectedDataValue |
	unidentifiedSubscriber
    }
    CODE
	local:7
}

/* updateLocation OPERATION ::= {
ARGUMENT SEQUENCE {
imsi OCTET STRING ( SIZE( 3 .. 8 ) ),
msc-Number [1] IMPLICIT OCTET STRING ( SIZE( 1 .. 20 ) ) ( SIZE( 1 .. 9 ) ),
vlr-Number OCTET STRING ( SIZE( 1 .. 20 ) ) ( SIZE( 1 .. 9 ) ),
lmsi [10] IMPLICIT OCTET STRING ( SIZE( 4 ) ) OPTIONAL,
extensionContainer SEQUENCE {
privateExtensionList [0] IMPLICIT SEQUENCE ( SIZE( 1 .. 10 ) ) OF
SEQUENCE {
extId MAP-EXTENSION .&extensionId ( {
,
...} ) ,
extType MAP-EXTENSION .&ExtensionType ( {
,
...} { @extId } ) OPTIONAL} OPTIONAL,
pcs-Extensions [1] IMPLICIT SEQUENCE {
... } OPTIONAL,
... } OPTIONAL,
... ,
vlr-Capability [6] IMPLICIT SEQUENCE {
supportedCamelPhases [0] IMPLICIT BIT STRING {
phase1 (0 ),
phase2 (1 ),
phase3 (2 ),
phase4 (3 )} ( SIZE( 1 .. 16 ) ) OPTIONAL,
extensionContainer SEQUENCE {
privateExtensionList [0] IMPLICIT SEQUENCE ( SIZE( 1 .. 10 ) ) OF
SEQUENCE {
extId MAP-EXTENSION .&extensionId ( {
,
...} ) ,
extType MAP-EXTENSION .&ExtensionType ( {
,
...} { @extId } ) OPTIONAL} OPTIONAL,
pcs-Extensions [1] IMPLICIT SEQUENCE {
... } OPTIONAL,
... } OPTIONAL,
... ,
solsaSupportIndicator [2] IMPLICIT NULL OPTIONAL,
istSupportIndicator [1] IMPLICIT ENUMERATED {
basicISTSupported ( 0 ),
istCommandSupported ( 1 ),
... } OPTIONAL,
superChargerSupportedInServingNetworkEntity [3] CHOICE {
sendSubscriberData [0] IMPLICIT NULL,
subscriberDataStored [1] IMPLICIT OCTET STRING ( SIZE( 1 .. 6 ) )} OPTIONAL,
longFTN-Supported [4] IMPLICIT NULL OPTIONAL,
supportedLCS-CapabilitySets [5] IMPLICIT BIT STRING {
lcsCapabilitySet1 (0 ),
lcsCapabilitySet2 (1 ),
lcsCapabilitySet3 (2 ),
lcsCapabilitySet4 (3 )} ( SIZE( 2 .. 16 ) ) OPTIONAL,
offeredCamel4CSIs [6] IMPLICIT BIT STRING {
o-csi (0 ),
d-csi (1 ),
vt-csi (2 ),
t-csi (3 ),
mt-sms-csi (4 ),
mg-csi (5 ),
psi-enhancements (6 )} ( SIZE( 7 .. 16 ) ) OPTIONAL} OPTIONAL,
informPreviousNetworkEntity [11] IMPLICIT NULL OPTIONAL,
cs-LCS-NotSupportedByUE [12] IMPLICIT NULL OPTIONAL,
v-gmlc-Address [2] IMPLICIT OCTET STRING ( SIZE( 5 .. 17 ) ) OPTIONAL,
add-info [13] IMPLICIT SEQUENCE {
imeisv [0] IMPLICIT OCTET STRING ( SIZE( 8 ) ),
skipSubscriberDataUpdate [1] IMPLICIT NULL OPTIONAL,
... } OPTIONAL}
RESULT SEQUENCE {
hlr-Number OCTET STRING ( SIZE( 1 .. 20 ) ) ( SIZE( 1 .. 9 ) ),
extensionContainer SEQUENCE {
privateExtensionList [0] IMPLICIT SEQUENCE ( SIZE( 1 .. 10 ) ) OF
SEQUENCE {
extId MAP-EXTENSION .&extensionId ( {
,
...} ) ,
extType MAP-EXTENSION .&ExtensionType ( {
,
...} { @extId } ) OPTIONAL} OPTIONAL,
pcs-Extensions [1] IMPLICIT SEQUENCE {
... } OPTIONAL,
... } OPTIONAL,
... ,
add-Capability NULL OPTIONAL}
ERRORS {
systemFailure |
dataMissing |
unexpectedDataValue |
unknownSubscriber |
roamingNotAllowed }
CODE local : 2
} */

END
