MTSMS { 
  ccitt recommendation q(773) modules (2) messages (1) version2 (2)
}

DEFINITIONS ::=

BEGIN

IMPORTS
  OPERATION,Error,Code
    FROM ROIO {joint-iso-itu-t
      remote-operations(4) informationObjects(5) version1(0)}
  DialoguePDU
    FROM DialoguePDUs {
     itu-t recommendation q 773 modules(2) dialoguePDUs(2) version1(1)};


MessageType  ::= CHOICE {
        undirectional   [APPLICATION 1] IMPLICIT Undirectional,
        begin           [APPLICATION 2] IMPLICIT Begin,
        end             [APPLICATION 4] IMPLICIT End,
        contiinue        [APPLICATION 5] IMPLICIT Continue,
        abort           [APPLICATION 7] IMPLICIT Abort
}


Undirectional ::= SEQUENCE {
        dialoguePortion DialoguePortion OPTIONAL,
        components      ComponentPortion 
}

Begin ::= SEQUENCE {
        otid            OrigTransactionID,
        dialoguePortion DialoguePortion OPTIONAL,
        components      ComponentPortion OPTIONAL 
}

End ::= SEQUENCE {
        dtid            DestTransactionID,
        dialoguePortion DialoguePortion OPTIONAL,
        components      ComponentPortion OPTIONAL
}

Continue ::= SEQUENCE {
        otid            OrigTransactionID,
        dtid            DestTransactionID,
        dialoguePortion DialoguePortion OPTIONAL,
        componenets     ComponentPortion OPTIONAL
}

Abort ::= SEQUENCE {
        dtid            DestTransactionID,
        reason CHOICE 
        {
                p-abortCause    P-AbortCause,
                dialoguePortion DialoguePortion
        } OPTIONAL
}
-- NOTE-When the Abort Message is generated by the Transaction sub-layer, a P-Abort Cause must be present.

DialoguePortion::= [APPLICATION 11] EXT

EXT ::= [UNIVERSAL 8] IMPLICIT SEQUENCE {
direct-reference OBJECT IDENTIFIER OPTIONAL,
indirect-reference INTEGER OPTIONAL,
data-value-descriptor ObjectDescriptor OPTIONAL,
encoding CHOICE {
single-ASN1-type [0] DialoguePDU, --
octet-aligned [1] IMPLICIT OCTET STRING,
arbitrary [2] IMPLICIT BIT STRING }}

-- The dialogue portion carries the dialogue control PDUs as valuse of the external data type.
-- The direct reference should be set to { ccitt recommendation q 773 as (1) dialogue-as(1) version(1)}
-- If structured dialogue is used and to { ccitt recommendation q 773 as (1) unidailogue-as(2) version(1)}
-- If unstructured dialogue is used or any user defined abstract syntax name when only user information 
-- is carried(eg. when user information is sent in a 1988 Abort mesage).

OrigTransactionID ::= [APPLICATION 8] IMPLICIT OCTET STRING(SIZE(1..4))

DestTransactionID ::= [APPLICATION 9] IMPLICIT OCTET STRING(SIZE(1..4))

P-AbortCause ::= [APPLICATION 10] IMPLICIT INTEGER {
        unrecognizedMessageType (0),
        unrecognizedTransactionID (1),
        badlyFormattedTransactionPortion (2),
        incorrectTransactionPortion (3),
        resourceLimitation (4)
}

-- COMPONENT PORTION. The last field in the transaction portion of the TCAP message is the Component Portion.
-- The Component Portion may be absent.

ComponentPortion::= [APPLICATION 12] IMPLICIT SEQUENCE SIZE(1..MAX) OF Component

-- Component Portion fields

-- COMPONENT TYPE. Recommendation X.229 defines four Application Protocol Data Units(APDUs).
-- TCAP adds returnResultNotLast to allow for the segmentation of a result.

Component ::= CHOICE {
        invoke                  [1] IMPLICIT Invoke,
        returnResultLast        [2] IMPLICIT ReturnResult,
        returnError             [3] IMPLICIT ReturnError,
        reject                  [4] IMPLICIT Reject,
        returnResultNotLast     [7] IMPLICIT ReturnResult
}

-- The Components are sequences of data elements.

-- InvokeTable OPERATION ::= {mo-ForwardSM}
Invoke ::= SEQUENCE {
        invokeID        InvokeIdType,
        linkedID        [0] IMPLICIT InvokeIdType OPTIONAL,
        opcode          Code,
        argument        ANY DEFINED BY opcode OPTIONAL
}

ReturnResult ::= SEQUENCE {
        invokeID InvokeIdType,
        result  SEQUENCE 
        {
                operationCode   OPERATION.&operationCode,
                parameter       ANY DEFINED BY operationCode 
        } OPTIONAL
}

ReturnError ::= SEQUENCE {
        invokeID        InvokeIdType,
--	errorCode	ERROR.&errorCode, 
	errorCode	Error, 
        parameter       ANY DEFINED BY errorCode OPTIONAL
}

Reject ::= SEQUENCE 
{
        invokeID CHOICE 
                {
                derivable       InvokeIdType,
                not-derivable   NULL
        },
        problem CHOICE 
                {
                generalProblem          [0] IMPLICIT GeneralProblem,
                invokeProblem           [1] IMPLICIT InvokeProblem,
                returnResultProblem     [2] IMPLICIT ReturnResultProblem,
                returnErrorProblem      [3] IMPLICIT ReturnErrorProblem
        }
}

InvokeIdType::= INTEGER(-128..127)

-- *****************
-- Problems
-- *****************

GeneralProblem ::= INTEGER {
        unrecognizedComponent (0),
        mistypedComponent (1),
        badlyStructuredComponent (2)
}

InvokeProblem ::= INTEGER {
        duplicateInvokeID (0),
        unrecognizedOperation (1),
        mistypedParameter (2),
        resourceLimitation (3),
        initiatingRelease (4),
        unrecognizedLinkedID (5),
        linkedResponceUnexpected (6),
        unexpectedLinkedOperation (7)
}

ReturnResultProblem ::= INTEGER {
        unrecognizedInvokeID (0),
        returnResultUnexpected (1),
        mistypedParameter (2)
}

ReturnErrorProblem ::= INTEGER {
        unrecognizedInvokeID (0),
        returnErrorUnexpected (1),
        unrecognizedError (2),
        unexpectedError (3),
        mistypedParameter (4)
}
MO-forward ::= SEQUENCE{
    sm-RP-DA CHOICE {
	imsi [0] IMPLICIT OCTET STRING ( SIZE( 3 .. 8 ) ),
        lmsi [1] IMPLICIT OCTET STRING ( SIZE( 4 ) ),
        serviceCentreAddressDA [4] IMPLICIT OCTET STRING ( SIZE( 1 .. 20 ) ),
        noSM-RP-DA [5] IMPLICIT NULL
    },
    sm-RP-OA CHOICE {
	msisdn [2] IMPLICIT OCTET STRING ( SIZE( 1 .. 20 ) ) ( SIZE( 1 .. 9 ) ),
        serviceCentreAddressOA [4] IMPLICIT OCTET STRING ( SIZE( 1 .. 20 ) ),
        noSM-RP-OA [5] IMPLICIT NULL
    },
    sm-RP-UI OCTET STRING ( SIZE( 1 .. 200 ) )
}
MT-forward ::= SEQUENCE {
  sm-RP-DA CHOICE {
    imsi [0] IMPLICIT OCTET STRING ( SIZE( 3 .. 8 ) ),
    lmsi [1] IMPLICIT OCTET STRING ( SIZE( 4 ) ),
    serviceCentreAddressDA [4] IMPLICIT OCTET STRING ( SIZE( 1 .. 20 ) ),
    noSM-RP-DA [5] IMPLICIT NULL
  },
  sm-RP-OA CHOICE {
    msisdn [2] IMPLICIT OCTET STRING ( SIZE( 1 .. 20 ) ) ( SIZE( 1 .. 9 ) ),
    serviceCentreAddressOA [4] IMPLICIT OCTET STRING ( SIZE( 1 .. 20 ) ),
    noSM-RP-OA [5] IMPLICIT NULL
  },
  sm-RP-UI OCTET STRING ( SIZE( 1 .. 200 ) ),
  moreMessagesToSend NULL OPTIONAL
}

END -- TCAPMessage
