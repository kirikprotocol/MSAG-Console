/* $Id$ */
/* ************************************************************************** *
 * Module: MAP Teleservice Codes.                                             *
 * -- 3GPP TS 29.002 V7.2.0 (2005-12)					      *
 * ************************************************************************** *
 * Author: R.V. Gerasimov                                                     *
 * ************************************************************************** */

-- 17.7.9	Teleservice Codes
MAP-TS-Code {
   itu-t(0) identified-organization (4) etsi (0) mobileDomain (0)
   gsm-Network (1) modules (3) map-TS-Code (19) version10 (10)}
DEFINITIONS ::= BEGIN

TeleserviceCode ::= OCTET STRING (SIZE (1))
-- This type is used to represent the code identifying a single
-- teleservice, a group of teleservices, or all teleservices. The
-- services are defined in TS GSM 22.003 [4].
-- The internal structure is defined as follows:

-- bits 87654321: group (bits 8765) and specific service
-- (bits 4321)

Ext-TeleserviceCode ::= OCTET STRING (SIZE (1..5))
-- This type is used to represent the code identifying a single
-- teleservice, a group of teleservices, or all teleservices. The
-- services are defined in TS GSM 22.003 [4].
-- The internal structure is defined as follows:

-- OCTET 1:
-- bits 87654321: group (bits 8765) and specific service
-- (bits 4321)

-- OCTETS 2-5: reserved for future use. If received the
    -- Ext-TeleserviceCode shall be
 	-- treated according to the exception handling defined for the
-- operation that uses this type.

-- Ext-TeleserviceCode includes all values defined for TeleserviceCode.

END -- MAP-TS-Code (Teleservice Codes)
