MAP-MobileServiceOperations {
  itu-t identified-organization (4) etsi (0) mobileDomain (0)
  gsm-Network (1) modules (3) map-MobileServiceOperations (5)
  version10 (10)}
DEFINITIONS
::=
BEGIN
IMPORTS
  OPERATION, ERROR
FROM Remote-Operations-Information-Objects {
  joint-iso-itu-t remote-operations(4)
  informationObjects(5) version1(0)}

  UpdateLocationArg,
  UpdateLocationRes,
  InsertSubscriberDataArg
FROM MAP-MS-DataTypes {
    itu-t identified-organization (4) etsi (0) mobileDomain (0)
    gsm-Network (1) modules (3) map-MS-DataTypes (11) version10 (10)}

    systemFailure,
    dataMissing,
    unexpectedDataValue,
    unknownSubscriber,
    roamingNotAllowed
FROM MAP-Errors {
   itu-t identified-organization (4) etsi (0) mobileDomain (0)
   gsm-Network (1) modules (3) map-Errors (10) version10 (10)}

;

updateLocation OPERATION ::= { --Timer m
    ARGUMENT
        UpdateLocationArg
    RESULT
        UpdateLocationRes
    ERRORS {
        unexpectedDataValue |
        dataMissing |
        unknownSubscriber |
        roamingNotAllowed
        systemFailure
    }
    CODE 
        local:2
}
cancelLocation OPERATION ::= { --Timer m
    ARGUMENT
	CancelLocationArg
    RESULT
	CancelLocationRes -- optional
    ERRORS {
	dataMissing |
	unexpectedDataValue
    }
    CODE
	local:3
}

insertSubscriberData OPERATION ::= { --Timer m
    ARGUMENT
	InsertSubscriberDataArg
    RESULT
	InsertSubscriberDataRes -- optional
    ERRORS {
	dataMissing |
	unexpectedDataValue |
	unidentifiedSubscriber
    }
    CODE
	local:7
}

END
