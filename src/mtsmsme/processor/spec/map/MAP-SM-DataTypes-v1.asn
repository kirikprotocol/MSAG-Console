-- unformatted text of asn modules ca be pbtained from
-- http://www.3gpp.org/ftp/Specs/archive/09_series/09.02/0902-3b0.zip
-- more formatted scanned text of asn modules ca be pbtained from
-- http://pda.etsi.org/exchangefolder/gsmts_0902sv031100p.pdf

MAP-SM-DataTypes-v1 DEFINITIONS IMPLICIT TAGS ::=

BEGIN

EXPORTS
	RoutingInfoForSM-Res-v1
;
IMPORTS
	ISDN-AddressString,
	IMSI

FROM MAP-CommonDataTypes {
   itu-t(0) identified-organization (4) etsi (0) mobileDomain (0)
   gsm-Network (1) modules (3) map-CommonDataTypes (18) version10 (10)}
;

RoutingInfoForSM-Res-v1 ::= SEQUENCE{
	imsi		IMSI,
			CHOICE{
				[0] IMPLICIT SEQUENCE{
	locationInfo				LocationInfo-v1,
	lMsId				LMsId-v1 OPTIONAL},
	forwardingData		[1] IMPLICIT ForwardingData-v1},
	mwd-Set			[2] IMPLICIT BOOLEAN OPTIONAL
}

LocationInfo-v1	 ::= CHOICE {
		roamingNumber	[0] IMPLICIT ISDN-AddressString,
		mscNumber		[1] IMPLICIT ISDN-AddressString}

LMsId-v1	 ::= OCTET STRING (SIZE (4))

ForwardingData-v1	 ::= SEQUENCE{
	forwardedToNumber	[5] IMPLICIT ISDN-AddressString,
	forwardingOptions	[6] IMPLICIT ForwardingOptions-v1 OPTIONAL
}
ForwardingOptions-v1	 ::= OCTET STRING (SIZE(1))
		-- Bit 8-7  Notification to forwarding party
		--          00  No notification
		--          01  notification with calling number identity
		--          10  notification without calling number identity
		-- Bit 6-5  Notification to calling party
		--          00 No notification
		--          01 Notification with forwarded-to number
		--          10 Notification without forwarded-to number

END
