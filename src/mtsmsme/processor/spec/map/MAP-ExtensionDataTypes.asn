/* $Id$ */
/* ************************************************************************** *
 * Module: MAP Extension data types.                                          *
 * -- 3GPP TS 29.002 V7.2.0 (2005-12)					      *
 * ************************************************************************** *
 * Author: R.V. Gerasimov                                                     *
 * ************************************************************************** */

-- 17.7.11	Extension data types
MAP-ExtensionDataTypes { itu-t(0) identified-organization(4) etsi(0)
    mobileDomain(0) gsm-Network(1) modules(3) map-ExtensionDataTypes(21) version10(10)}
DEFINITIONS IMPLICIT TAGS ::=
-- this is reduced version of original module containing only types required for IN-Manager
BEGIN

EXPORTS PrivateExtension, ExtensionContainer;

-- IOC for private MAP extensions
/*
MAP-EXTENSION ::= CLASS {
    &ExtensionType	OPTIONAL,
    &extensionId	OBJECT IDENTIFIER
}
*/
-- The length of the Object Identifier shall not exceed 16 octets and the
-- number of components of the Object Identifier shall not exceed 16
-- data types
ExtensionContainer ::= SEQUENCE {
    privateExtensionList	[0]	PrivateExtensionList OPTIONAL,
    pcs-Extensions		[1]	PCS-Extensions OPTIONAL,
  ...
}

PrivateExtensionList ::= SEQUENCE SIZE (1..maxNumOfPrivateExtensions)
				OF PrivateExtension

PrivateExtension ::= SEQUENCE {
/* GVR: original definition was:
    extId    MAP-EXTENSION.&extensionId({ExtensionSet}),
    extType  MAP-EXTENSION.&ExtensionType({ExtensionSet}{@extId}) OPTIONAL
 */
    extId	OBJECT IDENTIFIER,
    extType	ANY /* DEFINED BY extId */
}

maxNumOfPrivateExtensions INTEGER ::= 10

-- ExtensionSet MAP-EXTENSION ::= {
--    ...
    -- ExtensionSet is the set of all defined private extensions--
-- }

-- Unsupported private extensions shall be discarded if received.
PCS-Extensions ::= SEQUENCE {...}

END -- MAP-ExtensionDataTypes
