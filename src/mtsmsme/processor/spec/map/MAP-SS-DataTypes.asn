MAP-SS-DataTypes {
   itu-t identified-organization (4) etsi (0) mobileDomain (0)
   gsm-Network (1) modules (3) map-SS-DataTypes (14) version10 (10)}

DEFINITIONS

IMPLICIT TAGS

::=

BEGIN

EXPORTS
    SS-List,
    ForwardingOptions
;

IMPORTS
    SS-Code
FROM MAP-SS-Code {
   itu-t identified-organization (4) etsi (0) mobileDomain (0)
   gsm-Network (1) modules (3) map-SS-Code (15) version10 (10)}
;

ForwardingOptions ::= OCTET STRING (SIZE (1))

    -- bit 8: notification to forwarding party
    --	0  no notification
    --	1  notification

    -- bit 7: redirecting presentation
    --	0 no presentation  
    --	1  presentation

    -- bit 6: notification to calling party
    --	0  no notification
    --	1  notification

    -- bit 5: 0 (unused)

    -- bits 43: forwarding reason
    --	00  ms not reachable
    --	01  ms busy
    --	10  no reply
    --	11  unconditional when used in a SRI Result, 
    --	    or call deflection when used in a RCH Argument
    -- bits 21: 00 (unused)

SS-List ::= SEQUENCE SIZE (1..maxNumOfSS) OF SS-Code

maxNumOfSS  INTEGER ::= 30

END -- MAP-SS-DataTypes
